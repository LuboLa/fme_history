FME workspace S_KontrolniProgram_NEW1390r04.fmw
Title: MULTI to MULTI

Parameters:
- TIF = ""\\dfs03.cezdata.corp\CEZ\DJE\90E0003_ŘICT\3_data_a_reporting\CRD\EDU\FME\Kontrola\2.Kontrola\**\*.tif" "\\dfs03.cezdata.corp\CEZ\DJE\90E0003_ŘICT\3_data_a_reporting\CRD\EDU\FME\Kontrola\2.Kontrola\**\*.tiff""
- ExcelVystup = \\dfs03.cezdata.corp\CEZ\DJE\90E0003_ŘICT\3_data_a_reporting\CRD\EDU\FME\Kontrola   # Výstupní excel soubor
- SouboryKeKontrole = \\dfs03.cezdata.corp\CEZ\DJE\90E0003_ŘICT\3_data_a_reporting\CRD\EDU\FME\Kontrola\2.Kontrola\**\/   # INCLUDE_WEB_BROWSER Soubory ke kontrole
- Kontrolni_program = \\dfs03.cezdata.corp\CEZ\DJE\90E0003_ŘICT\3_data_a_reporting\CRD\EDU\FME\Podklady pro FME\Kontrolní program.xlsx   # Excel Kontrolní program
- SourceDataset_ACAD_13 = \\dfs03.cezdata.corp\CEZ\DJE\90E0003_ŘICT\3_data_a_reporting\CRD\EDU\FME\Kontrola\2.Kontrola\**\*.dwg   # Výkresy 2.Kontrola
- SourceDataset_REALDWG = \\dfs03.cezdata.corp\CEZ\DJE\90E0003_ŘICT\3_data_a_reporting\CRD\EDU\FME\Kontrola\2.Kontrola\**\*.dwg   # Výkresy 2. Kontrola RealDWG

Readers:
- TIFF_1: TIFF from $(TIF)
- PATH_2: PATH from $(SouboryKeKontrole)
- XLSXR_1: XLSXR from $(Kontrolni_program)
- ACAD_1: ACAD from $(SourceDataset_ACAD_13)
- REALDWG_1: REALDWG from $(SourceDataset_REALDWG)

Writers:
- XLSXW_1: XLSXW to $(ExcelVystup)

Creator
    GEOMTYPE = Geometry Object
    NUM = 1
    CREATED -> FeatureReader_2 [INITIATOR]

Bookmark: Vyhledání elektronických souborů v seznamech dokumentace
Note: Excel XLSX / Seznam dokumentace
FeatureReader_2
    ATTRS_TO_EXPOSE = fme_basename fme_dataset
    ATTR_ACCUM_MODE = Merge Initiator and Result
    ATTR_CONFLICT_RES = Use Result
    ATTR_IGNORE_NULLS = No
    COMBINE_GEOM = Use Result
    DATASET = ""\\dfs03.cezdata.corp\CEZ\DJE\90E0003_ŘICT\3_data_a_reporting\CRD\EDU\FME\Kontrola\2.Kontrola\**\*.xlsx" "\\dfs03.cezdata.corp\CEZ\DJE\90E0003_ŘICT\3_data_a_reporting\CRD\EDU\FME\Kontrola\2.Kontrola\**\*.xls""
    FORMAT = XLSXR
    INTERACT = NONE
    OUTPUT_FEATURES_DISPLAY = Schema and Data Features
    XLSXR_ALLOW_DOLLAR_SIGNS = YES
    XLSXR_APPLY_FILTERS = No
    XLSXR_CASE_SENSITIVE_FEATURE_TYPES = YES
    XLSXR_CREATE_FEATURE_TABLES_FROM_DATA = Yes
    XLSXR_EXCEL_COL_NAMES = YES
    XLSXR_EXPAND_MERGED_CELLS = Yes
    XLSXR_FORCE_DATETIME = NO
    XLSXR_QUERY_FEATURE_TYPES_FOR_MERGE_FILTERS = Yes
    XLSXR_READ_BLANK_AS = Missing
    XLSXR_READ_FORM_CONTROLS = NONE
    XLSXR_READ_RASTER_MODE = None
    XLSXR_REPLACE_ONLY_NEWLINES_CARRIAGE_RETURNS = YES
    XLSXR_SCAN_MAX_FEATURES = 1000
    XLSXR_SCHEMA_HANDLING_REVISION = 2
    XLSXR_SKIP_EMPTY_ROWS = YES
    XLSXR_STRIP_SHEETNAME_SPACES = YES
    XLSXR_TRIM_ATTR_NAME_WHITESPACE = Yes
    XLSXR_USE_CUSTOM_SCHEMA = NO
    XLSXR_XLSXR_EXPOSE_FORMAT_ATTRS = fme_basename,char(50) fme_dataset,char(50)
    <OTHER> -> AttributeExposer_2
AttributeExposer_2
    ATTR_LIST = B,C,D,E,F,G,H,xlsx_row_id,I
    -> Tester_14
Note: Odstraní prázdné řádky
Tester_14
    BOOL_OP = OR
    TEST_CLAUSE = TEST C NOT_ATTRIBUTE_IS_MISSING ""
    TEST_MODE = TEST
    PASSED -> AttributeSplitter_8
Note: Rozdělí sloupec B podle mezer, to z důvodu, že tam mají třeba špatně vložený další text k archivnímu číslu.
AttributeSplitter_8
    ATTR_NAME = C
    DELIMITER = " "
    DROP_EMPTY_PARTS = No
    LIST_NAME = _list
    TRIM_OPTION = Both
    -> FeatureJoiner_3 [LEFT]
    -> Junction
    -> Tester_4
    -> AttributeRemover_19
Note: Vyfiltruje z excelu DPS/SO
Tester_4
    BOOL_OP = OR
    TEST_CLAUSE = TEST @Value(xlsx_row_id) = 9
    TEST_MODE = TEST
    PASSED -> AttributeRenamer
Note: Pojmenuje atribut jako DPS - je zde obsažen i SO!
AttributeRenamer
    ATTR_TABLE = RENAME_SET_DEFAULT C > DPS
    MISSING_INPUT_ATTRS = REMOVE
    -> DuplicateFilter_28
DuplicateFilter_28
    INPUT_ORDERED_CHOICE = No
    KEYATTR = fme_basename
    UNIQUE -> FeatureJoiner_3 [RIGHT]
Note: Spojí DPS se souborem kterému náleží
FeatureJoiner_3
    ATTR_CONFLICT_RES = Use Left
    GEOMETRY_HANDLING = Use Left
    JOIN_KEYS = fme_basename fme_basename AUTO
    JOIN_MODE = Inner
    JOINED -> AttributeCreator_117
Note: Vytažení Archivního čísla
AttributeCreator_117
    ATTR_TABLE = SET_TO Archivni cislo = @Value(_list{0})
    -> Tester_16
Note: Filtr pouze el. souborů k vyhledávání
Tester_16
    BOOL_OP = COMPOSITE
    COMPOSITE_TEST = 1 AND 2 AND 3
    TEST_CLAUSE:
      TEST @Value(I) NOT_= El.soubor
      TEST @Value(I) NOT_= SEZNAM DOKUMENTACE JMA
      TEST @Value(xlsx_row_id) >= 27
    TEST_MODE = TEST
    PASSED -> AttributeSplitter_12
Note: Odstraní ještě z archivního čísla i čárku, tkerá se tam občas chybově objevuje
AttributeSplitter_12
    ATTR_NAME = Archivni cislo
    DELIMITER = ,
    DROP_EMPTY_PARTS = No
    LIST_NAME = _list
    TRIM_OPTION = Both
    -> AttributeCreator_16
Note: Vytvoří finální archivní číslo bez mezery a bez čárky na konci
AttributeCreator_16
    ATTR_TABLE = SET_TO Archivni cislo = @Value(_list{0})
    -> StringCaseChanger_8
Note: Dá všechna písmena malá
StringCaseChanger_8
    ATTRCHOICE = Selected Attributes
    ATTRLIST = Archivni cislo
    CHANGE_TYPE = lowercase
    -> Tester_10
    -> AttributeSplitter_6
Note: El. soubory, kde je počet A4 0 neprojdou
Tester_10
    BOOL_OP = COMPOSITE
    COMPOSITE_TEST = 1 AND 2 AND 3
    TEST_CLAUSE:
      CASE_INSENSITIVE_TEST @Value(H) > 0
      CASE_INSENSITIVE_TEST I ATTRIBUTE_HAS_A_VALUE ""
      CASE_INSENSITIVE_TEST H NOT_ATTRIBUTE_VALUE_NULL ""
    TEST_MODE = CASE_INSENSITIVE_TEST
    PASSED -> AttributeSplitter_19
    FAILED -> Tester_6
Note: Rozdělí sloupec G od mezery
AttributeSplitter_19
    ATTR_NAME = I
    DELIMITER = " "
    DROP_EMPTY_PARTS = No
    LIST_NAME = _list
    TRIM_OPTION = Both
    -> AttributeCreator_22
    -> AttributeCreator_23
Note: Pojmenuje list_0 ze sloupce G jako path_filename aby bylo pojmenováno jako data vycházející ze složky.
AttributeCreator_23
    ATTR_TABLE = SET_TO path_filename = @Value(_list{0})
    -> Tester_11
Note: To stejný jen list_1 a to kvůli tomu, že by mohlo být v řádku více souborů zapsaných
AttributeCreator_22
    ATTR_TABLE = SET_TO path_filename = @Value(_list{1})
    -> Tester_96
Note: Vezme jen soubory, takže text, který obsahuje +
Tester_96
    BOOL_OP = OR
    TEST_CLAUSE = CASE_INSENSITIVE_TEST @Value(path_filename) CONTAINS +
    TEST_MODE = CASE_INSENSITIVE_TEST
    PASSED -> AttributeSplitter_20
Note: Rozdělí název znovu
AttributeSplitter_20
    ATTR_NAME = path_filename
    DELIMITER = +
    DROP_EMPTY_PARTS = No
    LIST_NAME = _list8
    TRIM_OPTION = Both
    -> Tester_95
Tester_95
    BOOL_OP = OR
    TEST_CLAUSE = TEST @Value(_list8{0}) > 0
    TEST_MODE = TEST
    PASSED -> Tester_11
    FAILED -> Tester_11
    FAILED -> AttributeCreator_58
Note: Zkontroluje, že v evidenčním čísle není podtržítko nebo háčky
Tester_11
    BOOL_OP = COMPOSITE
    COMPOSITE_TEST = 1 AND 2 AND 3 AND 4 AND 5 AND 6 AND 7 AND 8 AND 9 AND 10
    TEST_CLAUSE:
      CASE_INSENSITIVE_TEST @Value(C) NOT_CONTAINS _
      CASE_INSENSITIVE_TEST @Value(C) NOT_CONTAINS ě
      CASE_INSENSITIVE_TEST @Value(C) NOT_CONTAINS š
      CASE_INSENSITIVE_TEST @Value(C) NOT_CONTAINS č
      CASE_INSENSITIVE_TEST @Value(C) NOT_CONTAINS ř
      CASE_INSENSITIVE_TEST @Value(C) NOT_CONTAINS ž
      CASE_INSENSITIVE_TEST @Value(C) NOT_CONTAINS ý
      CASE_INSENSITIVE_TEST @Value(C) NOT_CONTAINS á
      CASE_INSENSITIVE_TEST @Value(C) NOT_CONTAINS í
      CASE_INSENSITIVE_TEST @Value(C) NOT_CONTAINS é
    TEST_MODE = CASE_INSENSITIVE_TEST
    PASSED -> DuplicateFilter_5
    FAILED -> Tester_59
    FAILED -> DuplicateFilter_5
DuplicateFilter_5
    INPUT_ORDERED_CHOICE = No
    KEYATTR = path_filename
    UNIQUE -> FeatureJoiner_9 [LEFT]
    UNIQUE -> AttributeRenamer_3
    UNIQUE -> FeatureMerger_13 [SUPPLIER]
AttributeRenamer_3
    ATTR_TABLE = RENAME_SET_DEFAULT I > path_filename
    MISSING_INPUT_ATTRS = REMOVE
    -> StringCaseChanger_2
Note: Dá všechna písmena malá
StringCaseChanger_2
    ATTRCHOICE = Selected Attributes
    ATTRLIST = path_filename
    CHANGE_TYPE = lowercase
    -> FeatureMerger_2 [SUPPLIER]
    -> StringReplacer_3
Tester_59
    BOOL_OP = COMPOSITE
    COMPOSITE_TEST = 1 AND 2
    TEST_CLAUSE:
      TEST @Value(xlsx_row_id) >= 27
      TEST I ATTRIBUTE_HAS_A_VALUE ""
    TEST_MODE = TEST
    PASSED -> AttributeRenamer_10
Note: Odešle chybovou hlášku na špatně zapsanéa rchivní číslo
AttributeRenamer_10
    ATTR_TABLE = RENAME_SET_DEFAULT I > path_filename
    MISSING_INPUT_ATTRS = REMOVE
    -> AttributeSplitter_25
AttributeSplitter_25
    ATTR_NAME = path_filename
    DELIMITER = +
    DROP_EMPTY_PARTS = No
    LIST_NAME = rozdeleni
    TRIM_OPTION = Both
    -> Tester_75
Tester_75
    BOOL_OP = OR
    TEST_CLAUSE = CASE_INSENSITIVE_TEST @Value(rozdeleni{3}) CONTAINS 0
    TEST_MODE = TEST
    PASSED -> AttributeCreator_41
Note: 3A
AttributeCreator_41
    ATTR_TABLE:
      SET_TO KONTROLA = 3A
      SET_TO POPIS = Archivní číslo @Value(Archivni cislo) obsahuje nepovolený znak. Seznam dokumentace @Value(fme_basename).
      SET_TO DOKUMENTACE = @Value(path_filename)
    -> Sorter_5
Note: 4A
AttributeCreator_58
    ATTR_TABLE:
      SET_TO KONTROLA = 4A
      SET_TO POPIS = Dokumenty v seznamu dokumentace "@Value(fme_basename)" musí být rozděleny do řádků.
      SET_TO DOKUMENTACE = @Value(I)
    -> Sorter_5
Note: El. soubory, kde je počet A4 0 neprojdou
Tester_6
    BOOL_OP = OR
    TEST_CLAUSE = CASE_INSENSITIVE_TEST @Value(I) NOT_= 0
    TEST_MODE = CASE_INSENSITIVE_TEST
    PASSED -> Tester_81
Tester_81
    BOOL_OP = OR
    TEST_CLAUSE = CASE_INSENSITIVE_TEST I ATTRIBUTE_HAS_A_VALUE ""
    TEST_MODE = CASE_INSENSITIVE_TEST
    PASSED -> AttributeRenamer_8
Note: Odešle chybovou hlášku nevyplněn sloupec F
AttributeRenamer_8
    ATTR_TABLE = RENAME_SET_DEFAULT I > path_filename
    MISSING_INPUT_ATTRS = REMOVE
    -> DuplicateFilter_26
DuplicateFilter_26
    INPUT_ORDERED_CHOICE = No
    KEYATTR = fme_basename path_filename
    UNIQUE -> AttributeCreator_19
Note: 5A
AttributeCreator_19
    ATTR_TABLE:
      SET_TO KONTROLA = 5A
      SET_TO POPIS = V seznamu dokumentace @Value(fme_basename) není u dokumentu zapsán počet stran/formát ve sloupci H.
      SET_TO DOKUMENTACE = @Value(path_filename)
    -> Sorter_5
Junction
    -> Tester_42
    -> Tester_141
    -> Tester_44
    -> Tester_2
Note: Vyhledá DPS / SO
Tester_2
    BOOL_OP = OR
    TEST_CLAUSE:
      TEST @Value(B) = DPS:
      TEST @Value(B) = SO:
    TEST_MODE = TEST
    PASSED -> AttributeCreator_109
Note: Vytažení DPS/SO ze sloupce B
AttributeCreator_109
    ATTR_TABLE = SET_TO DPS/SO = @Value(_list{0})
    -> DuplicateFilter
    -> FeatureJoiner_9 [RIGHT]
Note: Odtud odchází DPS ze seznamu dokumentace k porovnání s DPS z M03.
DuplicateFilter
    INPUT_ORDERED_CHOICE = No
    KEYATTR = fme_basename
    UNIQUE -> AttributeRemover_34
    DUPLICATE -> AttributeCreator_115
AttributeRemover_34
    REMOVE_ATTRS = _list{0},B,C,F,G,xlsx_row_id,H,I,fme_basename
    -> FeatureJoiner_4 [RIGHT]
Note: 6A
AttributeCreator_115
    ATTR_TABLE:
      SET_TO KONTROLA = 6A
      SET_TO POPIS = V seznamu dokumentace nelze mít obsažen DPS a zároveň SO.
      SET_TO DOKUMENTACE = @Value(fme_basename)
    -> Sorter_5
Note: Sloučí archivní číslo a DPS pro vyhledávání v dokumentu
FeatureJoiner_9
    ATTR_CONFLICT_RES = Prefer Left
    GEOMETRY_HANDLING = Prefer Left
    JOIN_KEYS = fme_basename fme_basename AUTO
    JOIN_MODE = Inner
    JOINED -> AttributeSplitter_10
AttributeSplitter_10
    ATTR_NAME = I
    DELIMITER = +
    DROP_EMPTY_PARTS = No
    LIST_NAME = _list
    TRIM_OPTION = Both
    -> AttributeCreator_119
Note: Vytažení TL
AttributeCreator_119
    ATTR_TABLE = SET_TO TL = @Value(_list{2})
    -> Tester_63
Tester_63
    BOOL_OP = OR
    TEST_CLAUSE = TEST @Value(TL) = 01
    TEST_MODE = TEST
    PASSED -> Tester_12
Tester_12
    BOOL_OP = OR
    TEST_CLAUSE:
      CASE_INSENSITIVE_TEST @Value(I) CONTAINS .pdf
      CASE_INSENSITIVE_TEST @Value(I) CONTAINS .doc
      CASE_INSENSITIVE_TEST @Value(I) CONTAINS .docx
      CASE_INSENSITIVE_TEST @Value(I) CONTAINS .xls
      CASE_INSENSITIVE_TEST @Value(I) CONTAINS .xlsx
    TEST_MODE = CASE_INSENSITIVE_TEST
    PASSED -> DuplicateFilter_59
Note: Odchází k porovnání do tabulky: Převod DOC na PDF a vyhledávání textu v PDF souborech
DuplicateFilter_59
    INPUT_ORDERED_CHOICE = No
    KEYATTR = Archivni cislo
Note: Vyhledá složku v excelu (typ dokumentace - elektro, skř)
Tester_44
    BOOL_OP = OR
    TEST_CLAUSE = TEST @Value(C) = Složka:
    TEST_MODE = TEST
    PASSED -> StringCaseChanger_10
Note: Dá všechna písmena velká
StringCaseChanger_10
    ATTRCHOICE = Selected Attributes
    ATTRLIST = D
    CHANGE_TYPE = UPPERCASE
    -> AttributeRenamer_7
AttributeRenamer_7
    ATTR_TABLE = RENAME_SET_DEFAULT D > PROFESE
    MISSING_INPUT_ATTRS = REMOVE
    -> AttributeRemover_16
AttributeRemover_16
    REMOVE_ATTRS = _list{0},B,F,G,xlsx_row_id
    -> AttributeCreator_2
AttributeCreator_2
    ATTR_TABLE = SET_TO 1 = 1
    -> FeatureJoiner_5 [RIGHT]
Note: Vyhledá číslo JMA
Tester_42
    BOOL_OP = OR
    TEST_CLAUSE = TEST @Value(B) = JMA:
    TEST_MODE = TEST
    PASSED -> DuplicateFilter_51
Note: Pro popsání excel výsledkového souboru
DuplicateFilter_51
    INPUT_ORDERED_CHOICE = No
    KEYATTR = fme_dataset C
    UNIQUE -> AttributeRemover_33
AttributeRemover_33
    REMOVE_ATTRS = _list{0},A,C,F,fme_feature_type,G,xlsx_row_id
    -> FeatureJoiner_4 [LEFT]
Note: Všechny řádky, kde G obsahuje +
Tester_141
    BOOL_OP = OR
    TEST_CLAUSE = CASE_INSENSITIVE_TEST @Value(I) CONTAINS +
    TEST_MODE = CASE_INSENSITIVE_TEST
    PASSED -> Tester_123
Tester_123
    BOOL_OP = OR
    TEST_CLAUSE = TEST @Value(xlsx_row_id) >= 27
    TEST_MODE = TEST
    PASSED -> AttributeCreator_76
AttributeCreator_76
    ATTR_TABLE = SET_TO arch_cislos_ = @Value(C)
    -> StringReplacer
StringReplacer
    CASE = NO
    FIND_TEXT = /
    NO_MATCH = _FME_NO_OP_
    REGEXP = NO
    REPLACE_TEXT = _
    SRC_ATTRS = arch_cislos_
    -> Tester_124
Tester_124
    BOOL_OP = COMPOSITE
    COMPOSITE_TEST = 1 AND 2
    TEST_CLAUSE:
      TEST C ATTRIBUTE_HAS_A_VALUE ""
      TEST D ATTRIBUTE_HAS_A_VALUE ""
    TEST_MODE = TEST
    PASSED -> AttributeSplitter_34
AttributeSplitter_34
    ATTR_NAME = arch_cislos_
    DELIMITER = ,
    DROP_EMPTY_PARTS = No
    LIST_NAME = _listg
    TRIM_OPTION = Both
    -> AttributeSplitter_27
AttributeSplitter_27
    ATTR_NAME = I
    DELIMITER = +
    DROP_EMPTY_PARTS = No
    LIST_NAME = _list
    TRIM_OPTION = Both
    -> Tester_125
Tester_125
    BOOL_OP = OR
    TEST_CLAUSE = TEST @UpperCase(@Value(_listg{0})) = @UpperCase(@Value(_list{1}))
    TEST_MODE = TEST
    FAILED -> Tester_20
Tester_20
    BOOL_OP = OR
    TEST_CLAUSE = CASE_INSENSITIVE_TEST @Value(arch_cislos_) CONTAINS dsk
    TEST_MODE = CASE_INSENSITIVE_TEST
    FAILED -> AttributeCreator_62
Note: 7A
AttributeCreator_62
    ATTR_TABLE:
      SET_TO KONTROLA = 7A
      SET_TO POPIS = V seznamu dokumentace je rozpor mezi dodavatelským číslem "@Value(B)" a el. souborem "@Value(H)".
      SET_TO DOKUMENTACE = @Value(fme_basename)
    -> Sorter_5
Note: Porovná soubory ve složkách se seznam dokumentace
FeatureMerger_2
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(path_filename) @Value(path_filename) AUTO
    MERGE_TYPE = Attributes Only
    PROCESS_DUPS = YES
    REJECT_NULL_MISSING_KEYS = No
    SUPPLIERS_FIRST = No
    UNMERGED_REQUESTOR -> Tester_9
    UNUSED_SUPPLIER -> Tester_137
Note: Odstraní excel, to je vždy seznam dokumentace
Tester_9
    BOOL_OP = OR
    TEST_CLAUSE = TEST @Value(path_extension) = xlsx
    TEST_MODE = TEST
    FAILED -> AttributeCreator
AttributeCreator
    ATTR_TABLE = SET_TO nazev_porovnani_Aa = @Value(path_rootname)
    -> StringCaseChanger_4
StringCaseChanger_4
    ATTRCHOICE = Selected Attributes
    ATTRLIST = path_rootname
    CHANGE_TYPE = lowercase
    -> Tester_13
Note: Odebere soubory s velkým názvem, protože ty jsem tam vložila já manuálně.
Tester_13
    BOOL_OP = OR
    TEST_CLAUSE = TEST @Value(path_rootname) = @Value(nazev_porovnani_Aa)
    TEST_MODE = TEST
    PASSED -> AttributeCreator_43
Note: 1A
AttributeCreator_43
    ATTR_TABLE:
      SET_TO KONTROLA = 1A
      SET_TO POPIS = Soubor nalezen v předávané složce, ale nenalezen v seznamu dokumentace.  Aby @Value(path_filename) mohl být převzán do CŘD je nutný mít dokument uvedený v seznamu, proto prosím opravte seznam dokumentace. Pokud se dokument v seznamu vyskytuje, pravděpodobně je nějakým způsobem chybně zapsán (mezery, bez přípony, překlep, apod.)
      SET_TO DOKUMENTACE = @Value(path_filename)
    -> Sorter_5
Note: Odstraní předáváky a seznamy
Tester_137
    BOOL_OP = OR
    TEST_CLAUSE:
      CASE_INSENSITIVE_TEST @LowerCase(@Value(path_filename)) CONTAINS předávací
      CASE_INSENSITIVE_TEST @LowerCase(@Value(path_filename)) CONTAINS predavaci
      CASE_INSENSITIVE_TEST @LowerCase(@Value(path_filename)) CONTAINS h01
      CASE_INSENSITIVE_TEST @LowerCase(@Value(path_filename)) CONTAINS h02
      CASE_INSENSITIVE_TEST @LowerCase(@Value(path_filename)) CONTAINS seznamdokumentace
    TEST_MODE = CASE_INSENSITIVE_TEST
    PASSED -> AttributeCreator_42
Note: 2A
AttributeCreator_42
    ATTR_TABLE:
      SET_TO KONTROLA = 2A
      SET_TO POPIS = Soubor zapsán v seznamu dokumentace @Value(fme_basename), ale chybí v předávané složce.
      SET_TO DOKUMENTACE = @Value(path_filename)
    -> Sorter_5

Bookmark: Porovnání revize sloupec B a el. soubor sloupec G
AttributeRemover_19
    REMOVE_ATTRS = _list{0},B,C,fme_basename,fme_dataset,fme_feature_type
    -> Tester_102
Tester_102
    BOOL_OP = COMPOSITE
    COMPOSITE_TEST = 1 AND 2
    TEST_CLAUSE:
      TEST @Value(xlsx_row_id) >= 27
      TEST I ATTRIBUTE_HAS_A_VALUE ""
    TEST_MODE = TEST
    PASSED -> AttributeSplitter_26
AttributeSplitter_26
    ATTR_NAME = I
    DELIMITER = +
    DROP_EMPTY_PARTS = No
    LIST_NAME = _list
    TRIM_OPTION = Both
    -> AttributeSplitter_28
AttributeSplitter_28
    ATTR_NAME = _list{3}
    DELIMITER = .
    DROP_EMPTY_PARTS = No
    LIST_NAME = _tecka
    TRIM_OPTION = Both
    -> Tester_108
Tester_108
    BOOL_OP = OR
    TEST_CLAUSE = TEST @Value(_tecka{0}) = @Value(F)
    TEST_MODE = TEST
    FAILED -> AttributeCreator_14
Note: 17A
AttributeCreator_14
    ATTR_TABLE:
      SET_TO KONTROLA = 17A
      SET_TO POPIS = V seznamu dokumentace je rozpor v indexu ve sloupci F a I.
      SET_TO DOKUMENTACE = @Value(I)
    -> Sorter_5

Bookmark: Chybové hlášky
StringReplacer_3
    CASE = NO
    FIND_TEXT = /
    NO_MATCH = _FME_NO_OP_
    REGEXP = NO
    REPLACE_TEXT = _
    SRC_ATTRS = Archivni cislo
    -> FeatureMerger_12 [SUPPLIER]
AttributeSplitter_6
    ATTR_NAME = DPS
    DELIMITER = " "
    DROP_EMPTY_PARTS = No
    LIST_NAME = _list
    TRIM_OPTION = Both
    -> AttributeCreator_25
AttributeCreator_25
    ATTR_TABLE = SET_TO DPS/SO = @Value(_list{0})
    -> FeatureJoiner_11 [LEFT]
FeatureJoiner_4
    ATTR_CONFLICT_RES = Prefer Left
    GEOMETRY_HANDLING = Prefer Left
    JOIN_KEYS = fme_dataset fme_dataset AUTO
    JOIN_MODE = Inner
    JOINED -> FeatureJoiner_5 [LEFT]
FeatureJoiner_5
    ATTR_CONFLICT_RES = Prefer Left
    GEOMETRY_HANDLING = Prefer Left
    JOIN_KEYS = fme_dataset fme_dataset AUTO
    JOIN_MODE = Inner
    JOINED -> FeatureJoiner_13 [LEFT]
Note: Excel
Tester_80
    BOOL_OP = OR
    TEST_CLAUSE:
      CASE_INSENSITIVE_TEST @UpperCase(@Value(path_filename)) CONTAINS H01
      CASE_INSENSITIVE_TEST @UpperCase(@Value(path_filename)) CONTAINS H02
      CASE_INSENSITIVE_TEST @UpperCase(@Value(path_filename)) = XLSX
      CASE_INSENSITIVE_TEST @UpperCase(@Value(path_filename)) = XLS
    TEST_MODE = CASE_INSENSITIVE_TEST
    PASSED -> AttributeCreator_24
AttributeCreator_24
    ATTR_TABLE = SET_TO CESTA = @Value(fme_dataset)\@Value(path_filename)
    -> FeatureJoiner_13 [RIGHT]
FeatureJoiner_13
    ATTR_CONFLICT_RES = Prefer Left
    GEOMETRY_HANDLING = Prefer Left
    JOIN_KEYS = fme_dataset CESTA AUTO
    JOIN_MODE = Inner
    JOINED -> FeatureJoiner_11 [RIGHT]
    JOINED -> AttributeSplitter_14
FeatureJoiner_11
    ATTR_CONFLICT_RES = Prefer Left
    GEOMETRY_HANDLING = Prefer Left
    JOIN_KEYS = DPS/SO DPS/SO AUTO
    JOIN_MODE = Inner
    JOINED -> AttributeRemover_42
AttributeRemover_42
    REMOVE_ATTRS = _list{0},1,A,Archivni cislo,B,C,CESTA,DPS,F,fme_basename,fme_dataset,fme_feature_type,path_directory_unix,path_directory_windows,path_extension,path_filename,path_rootname,path_type,path_unix,path_windows,PROFESE,xlsx_row_id
    -> AttributeCreator_26
AttributeCreator_26
    ATTR_TABLE = SET_TO Soubor = @Value(H)
    -> StringCaseChanger_11
StringCaseChanger_11
    ATTRCHOICE = Selected Attributes
    ATTRLIST = Soubor
    CHANGE_TYPE = lowercase
    -> Tester_78
Note: Passed jsou SO, kde je třeba upravit / za tečku / Failes jsou DPS, kde je to dobře a pro název el. souboru to bude v poho
Tester_78
    BOOL_OP = OR
    TEST_CLAUSE = CASE_INSENSITIVE_TEST @Value(DPS/SO) CONTAINS /
    TEST_MODE = TEST
    PASSED -> AttributeSplitter_15
    FAILED -> FeatureMerger_18 [SUPPLIER]
AttributeSplitter_15
    ATTR_NAME = DPS/SO
    DELIMITER = /
    DROP_EMPTY_PARTS = No
    LIST_NAME = _list
    TRIM_OPTION = Both
    -> AttributeCreator_29
AttributeCreator_29
    ATTR_TABLE:
      SET_TO 1 část = @Value(_list{0})
      SET_TO 2 část = @Value(_list{1})
    -> AttributeCreator_30
Note: Ve SO přepis z / na .
AttributeCreator_30
    ATTR_TABLE = SET_TO DPS/SO = @Value(1 část).@Value(2 část)
    -> DuplicateFilter_33
DuplicateFilter_33
    INPUT_ORDERED_CHOICE = No
    KEYATTR = Soubor
    UNIQUE -> FeatureMerger_18 [SUPPLIER]
AttributeSplitter_14
    ATTR_NAME = C
    DELIMITER = ,
    DROP_EMPTY_PARTS = No
    LIST_NAME = _list
    TRIM_OPTION = Both
    -> AttributeCreator_28
AttributeCreator_28
    ATTR_TABLE:
      SET_TO JMA = @Value(_list{0})
      SET_TO 1 = @Value(1)
    -> AttributeSplitter_16
AttributeSplitter_16
    ATTR_NAME = C
    DELIMITER = " "
    DROP_EMPTY_PARTS = No
    LIST_NAME = _list
    TRIM_OPTION = Both
    -> AttributeCreator_31
AttributeCreator_31
    ATTR_TABLE = SET_TO JMA = @Value(_list{0})
    -> AttributeRemover_41
AttributeRemover_41
    REMOVE_ATTRS = _list{0},B,CESTA,fme_basename,fme_dataset,fme_feature_type,path_directory_unix,path_directory_windows,path_extension,path_filename,path_rootname,path_type,path_unix,path_windows,PROFESE
    -> DuplicateFilter_23
DuplicateFilter_23
    INPUT_ORDERED_CHOICE = No
    KEYATTR = JMA DPS/SO
    UNIQUE -> Tester_82
Tester_82
    BOOL_OP = OR
    TEST_CLAUSE = CASE_INSENSITIVE_TEST @Value(DPS/SO) CONTAINS /
    TEST_MODE = TEST
    PASSED -> AttributeSplitter_18
    FAILED -> AttributeSplitter_17
AttributeSplitter_18
    ATTR_NAME = DPS/SO
    DELIMITER = /
    DROP_EMPTY_PARTS = No
    LIST_NAME = _list
    TRIM_OPTION = Both
    -> AttributeCreator_34
AttributeCreator_34
    ATTR_TABLE:
      SET_TO 1 část = @Value(_list{0})
      SET_TO 2 část = @Value(_list{1})
    -> AttributeCreator_35
Note: Ve SO přepis z / na .
AttributeCreator_35
    ATTR_TABLE = SET_TO DPS/SO = @Value(1 část).@Value(2 část)
    -> AttributeSplitter_17
AttributeSplitter_17
    ATTR_NAME = JMA
    DELIMITER = ,
    DROP_EMPTY_PARTS = No
    LIST_NAME = _list
    TRIM_OPTION = Both
    -> AttributeCreator_33
AttributeCreator_33
    ATTR_TABLE = SET_TO JMA = @Value(_list{0})
    -> FeatureJoiner_10 [RIGHT]
    -> DuplicateFilter_21
DuplicateFilter_21
    INPUT_ORDERED_CHOICE = No
    KEYATTR = JMA
    UNIQUE -> AttributeCreator_13
AttributeCreator_13
    ATTR_TABLE = SET_TO JMAEXCEL = @Value(JMA)
    -> AttributeRemover_18
AttributeRemover_18
    REMOVE_ATTRS = DPS/SO,JMA,_list{0}
    -> FeatureJoiner_6 [RIGHT]
Note: Seřazení v excelu podle dokumentace
Sorter_5
    SORT_PARM = DOKUMENTACE NATURAL ASCENDING
    SORTED -> GeometryRemover_2
Note: Odstraní geometrii v dokumentech (tif apod)
GeometryRemover_2
    -> DuplicateFilter_17
DuplicateFilter_17
    INPUT_ORDERED_CHOICE = No
    KEYATTR = DOKUMENTACE KONTROLA POPIS
    UNIQUE -> FeatureMerger_18 [REQUESTOR]
FeatureMerger_18
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(DOKUMENTACE) @Value(Soubor) AUTO
    MERGE_TYPE = Attributes Only
    PROCESS_DUPS = YES
    REJECT_NULL_MISSING_KEYS = No
    SUPPLIERS_FIRST = No
    MERGED -> FeatureJoiner_10 [LEFT]
    UNMERGED_REQUESTOR -> AttributeRemover_4
AttributeRemover_4
    REMOVE_ATTRS = A,Archivni cislo,Archivni_cislo,B,C,F,G,_match,arch_cislos_,delka_ev_cislo,fme_basename,fme_color,fme_dataset,fme_feature_type,fme_fill_color,fme_geometry,fme_primary_axis,fme_rotation,fme_secondary_axis,fme_start_angle,fme_sweep_angle,fme_text_size,fme_text_string,fme_type,multi_reader_full_id,multi_reader_id,multi_reader_keyword,multi_reader_type,nazev_porovnani_Aa,path_directory_unix,path_extension,path_filename,path_filename_dupl,path_rootname,path_unix,path_windows,tiff_area_or_point,tiff_artist,tiff_byte_order,tiff_compression_method,tiff_copyright,tiff_datetime,tiff_documentname,tiff_hostcomputer,tiff_imagedescription,tiff_interleaving_type,tiff_maxsamplevalue,tiff_minsamplevalue,tiff_number_of_bits_per_cell,tiff_photometric_interpretation,tiff_pyramid_level{0}.num_columns,tiff_pyramid_level{0}.num_rows,tiff_pyramid_num_levels,tiff_resolutionunit,tiff_software,tiff_subdataset_description,tiff_subdataset_name,tiff_type,tiff_xresolution,tiff_yresolution,xlsx_row_id
    -> StringReplacer_2
StringReplacer_2
    CASE = NO
    FIND_TEXT = /
    NO_MATCH = _FME_NO_OP_
    REGEXP = NO
    REPLACE_TEXT = .
    SRC_ATTRS = DPS/SO,DPS
    -> Tester_32
    -> Tester_35
    -> Tester_64
Tester_32
    BOOL_OP = OR
    TEST_CLAUSE = TEST DPS/SO ATTRIBUTE_HAS_A_VALUE ""
    TEST_MODE = TEST
    PASSED -> AttributeSplitter_4
AttributeSplitter_4
    ATTR_NAME = DPS/SO
    DELIMITER = " "
    DROP_EMPTY_PARTS = No
    LIST_NAME = DPSSO
    TRIM_OPTION = Both
    -> AttributeCreator_32
AttributeCreator_32
    ATTR_TABLE:
      SET_TO DPS/SO = @Value(DPSSO{0})
      SET_TO JMA = JMA nespojeno
    -> FeatureJoiner_10 [LEFT]
Tester_35
    BOOL_OP = OR
    TEST_CLAUSE = TEST DPS ATTRIBUTE_HAS_A_VALUE ""
    TEST_MODE = TEST
    PASSED -> AttributeSplitter_7
AttributeSplitter_7
    ATTR_NAME = DPS
    DELIMITER = " "
    DROP_EMPTY_PARTS = No
    LIST_NAME = DPS
    TRIM_OPTION = Both
    -> AttributeCreator_5
AttributeCreator_5
    ATTR_TABLE:
      SET_TO DPS/SO = @Value(DPS{0})
      SET_TO JMA = JMA nespojeno
    -> FeatureJoiner_10 [LEFT]
Tester_64
    BOOL_OP = OR
    TEST_CLAUSE:
      TEST DPS ATTRIBUTE_HAS_A_VALUE ""
      TEST DPS/SO ATTRIBUTE_HAS_A_VALUE ""
    TEST_MODE = TEST
    FAILED -> AttributeCreator_10
AttributeCreator_10
    ATTR_TABLE = SET_TO DPS/SO = Nespojeno
    -> FeatureJoiner_10 [LEFT]
FeatureJoiner_10
    ATTR_CONFLICT_RES = Prefer Right
    GEOMETRY_HANDLING = Prefer Right
    JOIN_KEYS = DPS/SO DPS/SO AUTO
    JOIN_MODE = Inner
    JOINED -> Tester_19
    UNJOINED_LEFT -> AttributeSplitter_13
Tester_19
    BOOL_OP = OR
    TEST_CLAUSE = TEST POPIS ATTRIBUTE_HAS_A_VALUE ""
    TEST_MODE = TEST
    PASSED -> AttributeRemover_17
AttributeRemover_17
    REMOVE_ATTRS = 1 část,2 část,A,Archivni cislo,Archivni_cislo,B,C,CIS_ZM,DPSSO{0},DPS{0},F,G,INDEX,Soubor,TYP_VYKR,Zaokrouhleno,_code,_encoded,_list8{0},_list_{0},_listg{0},_listx{0},_listy{0},_list{0},_match,_xmin,_ymin,_zmin,arch_cislos_,archivni_cislo,autocad_entity,autocad_extmin_x,autocad_extmin_y,autocad_extmin_z,autocad_fillmode,autocad_font_typeface,autocad_layer,autocad_layout_name,autocad_linetype,autocad_original_color,autocad_original_layer,autocad_source_filename,autocad_space,autocad_text_size,autocad_width_factor,autocad_xscale,autocad_yscale,autocad_zscale,blokscale_xyz,delka_ev_cislo,fme_basename,fme_color,fme_dataset,fme_feature_type,fme_fill_color,fme_geometry,fme_primary_axis,fme_rotation,fme_secondary_axis,fme_start_angle,fme_sweep_angle,fme_text_size,fme_text_string,fme_type,list,multi_reader_full_id,multi_reader_id,multi_reader_keyword,multi_reader_type,nazev_porovnani_Aa,path_directory_unix,path_extension,path_filename,path_filename_dupl,path_rootname,path_unix,path_windows,tiff_area_or_point,tiff_artist,tiff_byte_order,tiff_compression_method,tiff_copyright,tiff_datetime,tiff_documentname,tiff_hostcomputer,tiff_imagedescription,tiff_interleaving_type,tiff_maxsamplevalue,tiff_minsamplevalue,tiff_number_of_bits_per_cell,tiff_photometric_interpretation,tiff_pyramid_level{0}.num_columns,tiff_pyramid_level{0}.num_rows,tiff_pyramid_num_levels,tiff_resolutionunit,tiff_software,tiff_subdataset_description,tiff_subdataset_name,tiff_type,tiff_xresolution,tiff_yresolution,xlsx_row_id,xmin,ymin
    -> FeatureJoiner_6 [LEFT]
AttributeSplitter_13
    ATTR_NAME = DOKUMENTACE
    DELIMITER = +
    DROP_EMPTY_PARTS = No
    LIST_NAME = arch.c
    TRIM_OPTION = Both
    -> FeatureMerger_12 [REQUESTOR]
FeatureMerger_12
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(arch.c{1}) @Value(Archivni cislo) AUTO
    MERGE_TYPE = Attributes Only
    PROCESS_DUPS = YES
    REJECT_NULL_MISSING_KEYS = No
    SUPPLIERS_FIRST = No
    MERGED -> Tester_65
    UNMERGED_REQUESTOR -> Tester_65
Tester_65
    BOOL_OP = OR
    TEST_CLAUSE = CASE_INSENSITIVE_TEST @LowerCase(@Value(DOKUMENTACE)) CONTAINS dsk
    TEST_MODE = CASE_INSENSITIVE_TEST
    FAILED -> AttributeRemover_6
AttributeRemover_6
    REMOVE_ATTRS = 1 část,2 část,A,Archivni cislo,Archivni_cislo,B,C,CIS_ZM,DPSSO{0},DPS{0},F,G,INDEX,Soubor,TYP_VYKR,Zaokrouhleno,_code,_encoded,_list8{0},_list_{0},_listg{0},_listx{0},_listy{0},_list{0},_match,_xmin,_ymin,_zmin,arch.c{0},arch_cislos_,archivni_cislo,autocad_entity,autocad_extmin_x,autocad_extmin_y,autocad_extmin_z,autocad_fillmode,autocad_font_typeface,autocad_layer,autocad_layout_name,autocad_linetype,autocad_original_color,autocad_original_layer,autocad_source_filename,autocad_space,autocad_text_size,autocad_width_factor,autocad_xscale,autocad_yscale,autocad_zscale,blokscale_xyz,delka_ev_cislo,fme_basename,fme_color,fme_dataset,fme_feature_type,fme_fill_color,fme_geometry,fme_primary_axis,fme_rotation,fme_secondary_axis,fme_start_angle,fme_sweep_angle,fme_text_size,fme_text_string,fme_type,list,multi_reader_full_id,multi_reader_id,multi_reader_keyword,multi_reader_type,nazev_porovnani_Aa,path_directory_unix,path_extension,path_filename,path_filename_dupl,path_rootname,path_unix,path_windows,tiff_area_or_point,tiff_artist,tiff_byte_order,tiff_compression_method,tiff_copyright,tiff_datetime,tiff_documentname,tiff_hostcomputer,tiff_imagedescription,tiff_interleaving_type,tiff_maxsamplevalue,tiff_minsamplevalue,tiff_number_of_bits_per_cell,tiff_photometric_interpretation,tiff_pyramid_level{0}.num_columns,tiff_pyramid_level{0}.num_rows,tiff_pyramid_num_levels,tiff_resolutionunit,tiff_software,tiff_subdataset_description,tiff_subdataset_name,tiff_type,tiff_xresolution,tiff_yresolution,xlsx_row_id,xmin,ymin,DPS/SO
    -> AttributeSplitter_21
AttributeSplitter_21
    ATTR_NAME = DPS
    DELIMITER = " "
    DROP_EMPTY_PARTS = No
    LIST_NAME = DPSSSS
    TRIM_OPTION = Both
    -> AttributeCreator_11
AttributeCreator_11
    ATTR_TABLE:
      SET_TO DPS/SO = @Value(DPSSSS{0})
      SET_TO 1 = 1
    -> Tester_66
Tester_66
    BOOL_OP = OR
    TEST_CLAUSE = TEST DPS/SO ATTRIBUTE_HAS_A_VALUE ""
    TEST_MODE = TEST
    PASSED -> FeatureJoiner_6 [LEFT]
    FAILED -> AttributeCreator_12
AttributeCreator_12
    ATTR_TABLE = SET_TO DPS/SO = Nespojeno
    -> FeatureJoiner_6 [LEFT]
FeatureJoiner_6
    ATTR_CONFLICT_RES = Prefer Left
    GEOMETRY_HANDLING = Prefer Left
    JOIN_KEYS = 1 1 AUTO
    JOIN_MODE = Inner
    JOINED -> StringReplacer_4
    UNJOINED_LEFT -> Tester_93
StringReplacer_4
    CASE = NO
    FIND_TEXT = /
    NO_MATCH = _FME_NO_OP_
    REGEXP = NO
    REPLACE_TEXT = _
    SRC_ATTRS = DPS/SO
    -> Tester_77
Tester_77
    BOOL_OP = AND
    TEST_CLAUSE:
      TEST POPIS ATTRIBUTE_HAS_A_VALUE ""
      TEST DOKUMENTACE ATTRIBUTE_HAS_A_VALUE ""
    TEST_MODE = TEST
    PASSED -> Tester_87
Tester_87
    BOOL_OP = AND
    TEST_CLAUSE:
      CASE_INSENSITIVE_TEST @LowerCase(@Value(autocad_block_name)) BEGINS_WITH *
      CASE_INSENSITIVE_TEST @Value(POPIS) BEGINS_WITH Výkres obsahuje nepovolený blok
    TEST_MODE = CASE_INSENSITIVE_TEST
    FAILED -> Konkretni chyba (writer XLSXW_1)
Konkretni chyba (writer XLSXW_1)
    attributes: DOKUMENTACE string(30), POPIS string(100), KONTROLA string(15)
Tester_93
    BOOL_OP = AND
    TEST_CLAUSE:
      TEST POPIS ATTRIBUTE_HAS_A_VALUE ""
      TEST DOKUMENTACE ATTRIBUTE_HAS_A_VALUE ""
    TEST_MODE = TEST
    PASSED -> Tester_94
Tester_94
    BOOL_OP = OR
    TEST_CLAUSE = TEST @Value(KONTROLA) NOT_= 1A
    TEST_MODE = TEST
    PASSED -> Konkretni chyba00 (writer XLSXW_1)
Konkretni chyba00 (writer XLSXW_1)
    attributes: DOKUMENTACE string(30), POPIS string(100), KONTROLA string(15)

Bookmark: Kontroluje soubory ve složkách
PATH (reader PATH_2)
    attributes: path_unix buffer, path_windows buffer, path_rootname buffer, path_filename buffer, path_extension buffer, path_directory_unix buffer, path_directory_windows buffer, path_type char(10)
    -> AttributeRemover_2
    -> Tester_69
    -> Tester_80
AttributeRemover_2
    REMOVE_ATTRS = path_type,fme_dataset,fme_feature_type,path_directory_windows
    -> Sorter_5
    -> StringCaseChanger
    -> StringSearcher
    -> Tester_25
    -> Tester_34
    -> Tester_92
Note: Vyfiltruje nepřípustné RTF formáty
Tester_34
    BOOL_OP = OR
    TEST_CLAUSE = TEST @Value(path_extension) = rtf
    TEST_MODE = TEST
    PASSED -> AttributeCreator_21
Note: 8A
AttributeCreator_21
    ATTR_TABLE:
      SET_TO KONTROLA = 8A
      SET_TO POPIS = Nepřípustný RTF formát.
      SET_TO DOKUMENTACE = @Value(path_filename)
    -> Sorter_5
Note: Vyfiltruje nepřípustné JPG formáty
Tester_25
    BOOL_OP = OR
    TEST_CLAUSE = CASE_INSENSITIVE_TEST @LowerCase(@Value(path_extension)) BEGINS_WITH jp
    TEST_MODE = TEST
    PASSED -> AttributeCreator_20
Note: 9A
AttributeCreator_20
    ATTR_TABLE:
      SET_TO KONTROLA = 9A
      SET_TO POPIS = Nepřípustný JPG formát.
      SET_TO DOKUMENTACE = @Value(path_filename)
    -> Sorter_5
Note: Vyfiltruje nepřípustné accdb
Tester_92
    BOOL_OP = OR
    TEST_CLAUSE = TEST @Value(path_extension) = accdb
    TEST_MODE = TEST
    PASSED -> AttributeCreator_54
Note: 10A
AttributeCreator_54
    ATTR_TABLE:
      SET_TO KONTROLA = 10A
      SET_TO POPIS = Formát accdb nelze předat zvlášť. Vložte jako přílohu do hlavního dokumentu.
      SET_TO DOKUMENTACE = @Value(path_filename)
    -> Sorter_5
Note: Dá všechna písmena malá
StringCaseChanger
    ATTRCHOICE = Selected Attributes
    ATTRLIST = path_filename
    CHANGE_TYPE = lowercase
    -> Tester_17
    -> FeatureJoiner_2 [RIGHT]
Note: Odstraní nepotřebné
Tester_17
    BOOL_OP = COMPOSITE
    COMPOSITE_TEST = 1 AND 2 AND 3 AND 4
    TEST_CLAUSE:
      CASE_INSENSITIVE_TEST @LowerCase(@Value(path_filename)) NOT_CONTAINS h01t
      CASE_INSENSITIVE_TEST @LowerCase(@Value(path_filename)) NOT_CONTAINS h02t
      CASE_INSENSITIVE_TEST @LowerCase(@Value(path_filename)) NOT_CONTAINS předávací
      CASE_INSENSITIVE_TEST @LowerCase(@Value(path_filename)) NOT_CONTAINS seznam
    TEST_MODE = CASE_INSENSITIVE_TEST
    PASSED -> Tester_18
Note: Odstraní nepotřebné
Tester_18
    BOOL_OP = OR
    TEST_CLAUSE:
      CASE_INSENSITIVE_TEST @Value(path_filename) CONTAINS .pdf
      CASE_INSENSITIVE_TEST @Value(path_filename) CONTAINS .dwg
      CASE_INSENSITIVE_TEST @Value(path_filename) CONTAINS .xlsx
      CASE_INSENSITIVE_TEST @Value(path_filename) CONTAINS .prj
      CASE_INSENSITIVE_TEST @Value(path_filename) CONTAINS .tif
      CASE_INSENSITIVE_TEST @Value(path_filename) CONTAINS .doc
      CASE_INSENSITIVE_TEST @Value(path_filename) CONTAINS .docx
      CASE_INSENSITIVE_TEST @Value(path_extension) = xls
      CASE_INSENSITIVE_TEST @Value(path_extension) = xlsx
    TEST_MODE = CASE_INSENSITIVE_TEST
    PASSED -> DuplicateFilter_4
Note: Detekuje duplicitní prvky na základě názvu souboru.
DuplicateFilter_4
    INPUT_ORDERED_CHOICE = No
    KEYATTR = path_filename
    UNIQUE -> FeatureMerger_2 [REQUESTOR]
    DUPLICATE -> AttributeCreator_4
Note: Nový atribut / duplicitni_soubor
AttributeCreator_4
    ATTR_TABLE = SET_TO path_filename_dupl = @Value(path_filename)
    -> FeatureJoiner_2 [LEFT]
Note: vypisuje cestu k duplicitnímu uložení souborů
FeatureJoiner_2
    ATTR_CONFLICT_RES = Use Right
    GEOMETRY_HANDLING = Use Right
    JOIN_KEYS = path_filename_dupl path_filename AUTO
    JOIN_MODE = Left
    JOINED -> AttributeCreator_45
Note: 11A
AttributeCreator_45
    ATTR_TABLE:
      SET_TO KONTROLA = 11A
      SET_TO POPIS = Soubor se v předáváné dokumentaci vyskytuje vícekrát.
      SET_TO DOKUMENTACE = @Value(path_filename)
    -> Sorter_5
Note: Filtruje zdrojové názvy "+"
StringSearcher
    CASE = no
    MATCHED_RESULT_ATTR = _match
    REGEXP = [%+%]
    STRING_TO_SEARCH = @Value(path_rootname)
    MATCHED -> AttributeSplitter_9
    NOT_MATCHED -> Tester_7
Note: Rozdělí rootname
AttributeSplitter_9
    ATTR_NAME = path_rootname
    DELIMITER = +
    DROP_EMPTY_PARTS = No
    LIST_NAME = _list
    TRIM_OPTION = Both
    -> AttributeCreator_112
    -> Tester_76
    -> Tester_91
Note: Moc plusítek v názvu, chybný
Tester_91
    BOOL_OP = OR
    TEST_CLAUSE = TEST _list{4} ATTRIBUTE_HAS_A_VALUE ""
    TEST_MODE = TEST
    PASSED -> AttributeCreator_44
Tester_76
    BOOL_OP = OR
    TEST_CLAUSE = TEST _list{3} ATTRIBUTE_HAS_A_VALUE ""
    TEST_MODE = TEST
    FAILED -> Tester_136
Note: Vytažení archivního čísla ze zdrojového názvu souboru
AttributeCreator_112
    ATTR_TABLE = SET_TO Archivni_cislo = @Value(_list{1})
    -> Sorter_5
    -> StringLengthCalculator
    -> Tester_48
Note: Vypočítá délku řetězce
StringLengthCalculator
    LENGTH_ATTR = delka_ev_cislo
    SRC_ATTR = Archivni_cislo
    -> Tester_5
Note: Pokud více než 15 znaků, tak failed a vypsání chyby do txt.
Tester_5
    BOOL_OP = OR
    TEST_CLAUSE = TEST @Value(delka_ev_cislo) < 16
    TEST_MODE = TEST
    FAILED -> Tester_72
Note: A4 - Na čtvrté pozici za + je 0
Tester_72
    BOOL_OP = OR
    TEST_CLAUSE = TEST @Value(_list{3}) = 0
    TEST_MODE = TEST
    PASSED -> DuplicateFilter_22
Note: pokud jde o revidovaný výkres, který je starý, tak neplatí povinnost 15 znaků
DuplicateFilter_22
    INPUT_ORDERED_CHOICE = No
    KEYATTR = path_directory_unix path_rootname
    UNIQUE -> Tester_21
Tester_21
    BOOL_OP = OR
    TEST_CLAUSE:
      CASE_INSENSITIVE_TEST @LowerCase(@Value(path_rootname)) CONTAINS h01
      CASE_INSENSITIVE_TEST @LowerCase(@Value(path_rootname)) CONTAINS h02
      CASE_INSENSITIVE_TEST @LowerCase(@Value(path_rootname)) CONTAINS předávací
      CASE_INSENSITIVE_TEST @LowerCase(@Value(path_rootname)) CONTAINS predavaci
    TEST_MODE = TEST
    FAILED -> AttributeCreator_46
Note: 13A
AttributeCreator_46
    ATTR_TABLE:
      SET_TO KONTROLA = 13A
      SET_TO POPIS = Archivní číslo, obsahuje nepovolený počet znaků (více než 15).
      SET_TO DOKUMENTACE = @Value(path_filename)
    -> Sorter_5
Note: Pouze PDF (doc) pro porovnání archivního čísla z názvu dokumentu spolu s vnitřkem dokumentu
Tester_48
    BOOL_OP = OR
    TEST_CLAUSE:
      TEST @Value(path_extension) = pdf
      TEST @Value(path_extension) = doc
      TEST @Value(path_extension) = docx
    TEST_MODE = TEST
    PASSED -> DuplicateFilter_24
DuplicateFilter_24
    INPUT_ORDERED_CHOICE = No
    KEYATTR = path_rootname
    UNIQUE -> StringCaseChanger_9
Note: Dá všechna písmena malá
StringCaseChanger_9
    ATTRCHOICE = Selected Attributes
    ATTRLIST = Archivni_cislo
    CHANGE_TYPE = lowercase
    -> FeatureMerger_13 [REQUESTOR]
FeatureMerger_13
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(path_filename) @Value(H) AUTO
    MERGE_TYPE = Attributes Only
    PROCESS_DUPS = YES
    REJECT_NULL_MISSING_KEYS = No
    SUPPLIERS_FIRST = No
    MERGED -> Tester_79
Tester_79
    BOOL_OP = OR
    TEST_CLAUSE = TEST @Value(path_extension) = pdf
    TEST_MODE = TEST
    PASSED -> AttributeCreator_7
AttributeCreator_7
    ATTR_TABLE = SET_TO Archivni_cislo = @LowerCase(@Value(Archivni_cislo))
    -> FeatureJoiner [LEFT]
Note: Path_extension
Tester_7
    BOOL_OP = OR
    TEST_CLAUSE:
      TEST @Value(path_extension) = pdf
      TEST @Value(path_extension) = xlsx
      TEST @Value(path_extension) = doc
      TEST @Value(path_extension) = docx
      TEST @Value(path_extension) = xls
      TEST @Value(path_extension) = dwg
    TEST_MODE = TEST
    PASSED -> Tester_8
Note: Vyfiltruje nesprávné názvy souborů
Tester_8
    BOOL_OP = OR
    TEST_CLAUSE:
      TEST @LowerCase(@Value(path_filename)) CONTAINS předávaci
      TEST @LowerCase(@Value(path_filename)) CONTAINS h01
      TEST @LowerCase(@Value(path_filename)) CONTAINS h02
      CASE_INSENSITIVE_TEST @LowerCase(@Value(path_filename)) CONTAINS dps
      TEST @LowerCase(@Value(path_filename)) = prj
      TEST @LowerCase(@Value(path_filename)) = 08
      CASE_INSENSITIVE_TEST @LowerCase(@Value(path_filename)) CONTAINS predavaci
    TEST_MODE = PER_TEST
    FAILED -> Tester_136
Note: Nechceme předáváky a seznamy
Tester_136
    BOOL_OP = OR
    TEST_CLAUSE:
      CASE_INSENSITIVE_TEST @LowerCase(@Value(path_rootname)) CONTAINS předávací
      CASE_INSENSITIVE_TEST @LowerCase(@Value(path_rootname)) CONTAINS predavaci
      CASE_INSENSITIVE_TEST @LowerCase(@Value(path_rootname)) CONTAINS h01
      CASE_INSENSITIVE_TEST @LowerCase(@Value(path_rootname)) CONTAINS h02
      CASE_INSENSITIVE_TEST @LowerCase(@Value(path_rootname)) CONTAINS seznamdokumentace
      CASE_INSENSITIVE_TEST @LowerCase(@Value(path_rootname)) CONTAINS seznam dokumentace
      CASE_INSENSITIVE_TEST @LowerCase(@Value(path_rootname)) CONTAINS tl
      CASE_INSENSITIVE_TEST @LowerCase(@Value(path_rootname)) CONTAINS pd změn
      CASE_INSENSITIVE_TEST @LowerCase(@Value(path_rootname)) CONTAINS pd zmen
    TEST_MODE = CASE_INSENSITIVE_TEST
    FAILED -> Tester_84
Tester_84
    BOOL_OP = OR
    TEST_CLAUSE:
      TEST @Value(path_extension) = pdf
      TEST @Value(path_extension) = xlsx
      TEST @Value(path_extension) = xls
      TEST @Value(path_extension) = doc
      TEST @Value(path_extension) = dwg
      TEST @Value(path_extension) = docx
    TEST_MODE = TEST
    PASSED -> AttributeCreator_44
Note: 12A
AttributeCreator_44
    ATTR_TABLE:
      SET_TO KONTROLA = 12A
      SET_TO POPIS = Název souboru neodpovídá správnému pojmenování dle ST 0093.
      SET_TO DOKUMENTACE = @Value(path_filename)
    -> Sorter_5
Note: PDF
Tester_69
    BOOL_OP = OR
    TEST_CLAUSE = TEST @Value(path_extension) = pdf
    TEST_MODE = TEST
    PASSED -> FeatureReader [INITIATOR]
Note: Načtení všech PDF
FeatureReader
    ATTRS_TO_EXPOSE = pdf_type fme_feature_type pdf_page_text fme_basename pdf_page_number fme_type PDF_words
    ATTR_ACCUM_MODE = Only Use Result
    COMBINE_GEOM = Use Result
    DATASET = @Value(path_windows)
    FORMAT = PDF2D
    INTERACT = <No Spatial Filter>
    OUTPUT_FEATURES_DISPLAY = Schema and Data Features
    PDF2D_FEATURE_TYPE_CATEGORY = OCG_LAYERS
    PDF2D_PAGE_NUMBERS_START_AT_ONE = YES
    PDF2D_QUERY_FEATURE_TYPES_FOR_MERGE_FILTERS = Yes
    PDF2D_READ_NONSPATIAL = YES
    PDF2D_READ_NONSPATIAL_TEXT = YES
    PDF2D_READ_RASTERIZED_PAGES = NO
    PDF2D_READ_SPATIAL = NO
    PDF2D_READ_TAGGED_TABLES = NO
    PDF2D_REORDER_BANDS_TO_RGBA = YES
    PDF2D_TRIM_OCG_NAMES = YES
    PDF2D_USE_PASSWORD = NO
    PDF2D_USE_SEARCH_ENVELOPE = NO
    <OTHER> -> Tester_3
Note: Vyfiltrování textů ze stran
Tester_3
    BOOL_OP = OR
    TEST_CLAUSE = TEST @Value(fme_feature_type) = pdf_text_pages
    TEST_MODE = TEST
    PASSED -> AttributeSplitter
Note: Rozdělení textů po slovech (mezera)
AttributeSplitter
    ATTR_NAME = pdf_page_text
    DELIMITER = " "
    DROP_EMPTY_PARTS = No
    LIST_NAME = _list
    TRIM_OPTION = Both
    -> Tester_67
Note: Tady nám to filtruje pouze první stránku dokumentu
Tester_67
    BOOL_OP = OR
    TEST_CLAUSE = TEST @Value(pdf_page_number) = 1
    TEST_MODE = TEST
    PASSED -> ListExploder
Note: Rozdělení
ListExploder
    ATTR_ACCUM_MODE = Merge List Attributes
    ATTR_CONFLICT_RES = Use List Attribute Values
    INDEX_ATTR = RADEK
    LIST_ATTR = _list{}
    ELEMENTS -> AttributeSplitter_2
Note: Rozdělení textů po řádcích (enter)
AttributeSplitter_2
    ATTR_NAME = _list
    DELIMITER = "\n"
    DROP_EMPTY_PARTS = No
    LIST_NAME = _list2
    TRIM_OPTION = Both
    -> ListExploder_2
Note: Rozdělení
ListExploder_2
    ATTR_ACCUM_MODE = Merge List Attributes
    ATTR_CONFLICT_RES = Use List Attribute Values
    INDEX_ATTR = RADEK2
    LIST_ATTR = _list2{}
    ELEMENTS -> StringCaseChanger_3
Note: Dá všechna písmena malá
StringCaseChanger_3
    ATTRCHOICE = Selected Attributes
    ATTRLIST = _list2
    CHANGE_TYPE = lowercase
    -> Tester_22
    -> AttributeCreator_8
AttributeCreator_8
    ATTR_TABLE = SET_TO _list2 = @LowerCase(@Value(_list2))
    -> FeatureJoiner [RIGHT]
Tester_22
    BOOL_OP = OR
    TEST_CLAUSE = CASE_INSENSITIVE_TEST @Value(_list2) CONTAINS +
    TEST_MODE = TEST
    PASSED -> AttributeSplitter_3
AttributeSplitter_3
    ATTR_NAME = _list2
    DELIMITER = +
    DROP_EMPTY_PARTS = No
    LIST_NAME = arch
    TRIM_OPTION = Both
    -> AttributeCreator_9
AttributeCreator_9
    ATTR_TABLE = SET_TO _list2 = @LowerCase(@Value(arch{1}))
    -> FeatureJoiner [RIGHT]
Note: Porovná archivní číslo uvnitř dokumentu spolu se zdrojovým názvem dokumentu.
FeatureJoiner
    ATTR_CONFLICT_RES = Prefer Left
    GEOMETRY_HANDLING = Prefer Left
    JOIN_KEYS = Archivni_cislo _list2 AUTO
    JOIN_MODE = Inner
    UNJOINED_LEFT -> DuplicateFilter_2
DuplicateFilter_2
    INPUT_ORDERED_CHOICE = No
    KEYATTR = path_filename
    UNIQUE -> Tester_70
Note: Dokumenty, které obsahují jen čísla jsou vždy skenované pracáky
Tester_70
    BOOL_OP = OR
    TEST_CLAUSE = CASE_SENSITIVE_TEST @Value(_list{1}) NOT_CONTAINS_REGEX ^\d+$
    TEST_MODE = CASE_SENSITIVE_TEST
    PASSED -> Tester_71
Note: Jde o protokoly IaC Energa, kde jsou vždy archivní čísla ve skenu, proto se ukážou jako chyba, ale není to chyba.
Tester_71
    BOOL_OP = COMPOSITE
    COMPOSITE_TEST = 1 AND 2
    TEST_CLAUSE:
      CASE_INSENSITIVE_TEST @UpperCase(@Value(path_rootname)) NOT_CONTAINS ZE0
      CASE_INSENSITIVE_TEST @UpperCase(@Value(path_rootname)) NOT_CONTAINS ZKX0
    TEST_MODE = CASE_INSENSITIVE_TEST
    PASSED -> Tester_15
Note: Konečné zkoušky/kalibrační listy - mají vždy archivní číslo / Domluva s Majkou, zatím nutný, aby u těchto dokumentů byly arch. čísla / Nutné doplnění
Tester_15 [off]
    BOOL_OP = AND
    TEST_CLAUSE:
      CASE_INSENSITIVE_TEST @Value(path_rootname) NOT_CONTAINS J
      CASE_INSENSITIVE_TEST @Value(path_rootname) NOT_CONTAINS .C.
    TEST_MODE = TEST
    PASSED -> Tester_83
Tester_83
    BOOL_OP = OR
    TEST_CLAUSE = TEST @LowerCase(@Value(path_filename)) NOT_= dsk
    TEST_MODE = TEST
    PASSED -> AttributeCreator_3
Note: 14A
AttributeCreator_3
    ATTR_TABLE:
      SET_TO KONTROLA = 14A
      SET_TO POPIS = V dokumentu nenalezeno archivní číslo "@Value(Archivni_cislo)" dokumentu. Může jít o špatné vyčtení programu, protože je dokument pouze scan. Pokud archivní číslo máte, chybu ignorujte. Pokud je chyba oprávněná, zapište archivní číslo do dokumentu.
      SET_TO DOKUMENTACE = @Value(path_filename)
    -> Sorter_5

Bookmark: Kontrola TIF souboru
TIFF (reader TIFF_1)
    -> Tester
Note: Kontroluje 400 dPi, stupně šedi - 1 LZW
Tester
    BOOL_OP = COMPOSITE
    COMPOSITE_TEST = 1 AND 2 AND 3 AND 4
    TEST_CLAUSE:
      TEST @Value(tiff_xresolution) >= 300
      TEST @Value(tiff_yresolution) >= 300
      TEST @Value(tiff_number_of_bits_per_cell) = 1
      TEST @Value(fme_dataset) ENDS_WITH .tif
    TEST_MODE = TEST
    FAILED -> AttributeRenamer_9
AttributeRenamer_9
    ATTR_TABLE = RENAME_SET_DEFAULT fme_basename > path_filename
    MISSING_INPUT_ATTRS = REMOVE
    -> AttributeCreator_48
Note: 16A
AttributeCreator_48
    ATTR_TABLE:
      SET_TO KONTROLA = 16A
      SET_TO POPIS = Vlastnosti souboru, neodpovídají správnosti. Hodnoty musí být stejné: Horizontální rozlišení 300 dpi; Vertikální rozlišení 300 dpi; Bitová hloubka 1.
      SET_TO DOKUMENTACE = @Value(path_filename)
    -> Sorter_5

Bookmark: New Bookmark
O_RARO (reader REALDWG_1)
    attributes: ARCH_C char(255), BALIK char(1), CIS_ZM char(255), DATUM char(255), INDEX char(255), JMENO char(255), KONTROLOVAL char(255), LIST char(255), MERITKO char(255), NAZEV_1 char(255), NAZEV_2 char(255), NAZEV_CASTI char(255), POPIS char(255), POPIS_1 char(1), POPIS_2 char(1), PUV_VYKR char(255), REZERVA1 char(7), REZERVA2 char(7), REZERVA3 char(9), REZERVA_1 char(12), REZERVA_2 char(12), REZERVA_3 char(8), SCHVALIL char(11), SO_DPS char(9), TPO char(255), TYP_VYKR char(5), VYPRACOVAL char(255), DD char(3), KTD number(4,0), LIST_N number(2,0),
      NAME-1 char(1), NAME-2 char(1), NAZEV_N char(255), NEV_TECHNOL_OZN char(9), NEV_TYP char(1), PCN char(1), PCN1 char(2), PCN2 char(2), TECHNOL_OZN number(6,0), TYP char(1), TYP_PODTYP char(8)
    -> DuplicateFilter_20
DuplicateFilter_20
    INPUT_ORDERED_CHOICE = No
    KEYATTR = CIS_ZM fme_basename fme_dataset fme_feature_type INDEX TYP_VYKR
    UNIQUE -> AttributeSplitter_5
    UNIQUE -> AttributeSplitter_22
AttributeSplitter_5
    ATTR_NAME = fme_basename
    DELIMITER = +
    DROP_EMPTY_PARTS = No
    LIST_NAME = _list
    TRIM_OPTION = Both
    -> CharacterCodeExtractor
    -> DuplicateFilter_32
Note: Na třetí pozici za + je 00 nebo 01
Tester_74
    BOOL_OP = OR
    TEST_CLAUSE:
      TEST @Value(_list{2}) = 00
      TEST @Value(_list{2}) = 01
    TEST_MODE = TEST
    PASSED -> Tester_24
Note: Vyfiltruje atributy které mají Číslo změny a Index
Tester_24
    BOOL_OP = AND
    TEST_CLAUSE:
      TEST CIS_ZM ATTRIBUTE_HAS_A_VALUE ""
      TEST INDEX ATTRIBUTE_HAS_A_VALUE ""
    TEST_MODE = TEST
    PASSED -> DuplicateFilter_19
DuplicateFilter_19
    INPUT_ORDERED_CHOICE = No
    KEYATTR = fme_basename _encoded CIS_ZM
    UNIQUE -> Tester_27
Note: Porovná jestli index v razítku je stejný jako o abecedu snížený rootname a tam musí být cis_zm
Tester_27
    BOOL_OP = OR
    TEST_CLAUSE = TEST @Value(INDEX) = @Value(_encoded)
    TEST_MODE = TEST
    PASSED -> FeatureMerger_11 [REQUESTOR]
    FAILED -> FeatureMerger_11 [SUPPLIER]
FeatureMerger_11
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(fme_basename) @Value(fme_basename) AUTO
    MERGE_TYPE = Attributes Only
    PROCESS_DUPS = YES
    REJECT_NULL_MISSING_KEYS = No
    SUPPLIERS_FIRST = No
    UNUSED_SUPPLIER -> Tester_26
Note: Vytáhne indexy a, protože tam číslo změny zatím nemůže být, ale musí tam být zadaný balík. / Pokud existují výkresy s pořadovým číslem listu, tak tam změna revize již není obsažena
Tester_26
    BOOL_OP = OR
    TEST_CLAUSE = TEST @Value(_encoded) != /
    TEST_MODE = TEST
    PASSED -> DuplicateFilter_3
DuplicateFilter_3
    INPUT_ORDERED_CHOICE = No
    KEYATTR = fme_basename
    UNIQUE -> AttributeCreator_51
Note: 1V
AttributeCreator_51
    ATTR_TABLE:
      SET_TO KONTROLA = 1V
      SET_TO POPIS = Výkres nemá uvedené číslo změny u předchozí revize. Pravděpodobně výkres nebyl převzat z CŘD. Pokud výkres ani v CŘD nemá číslo změny, tuto kontrolu ignorujte.
      SET_TO DOKUMENTACE = @Value(fme_basename).dwg
    -> Junction_4
DuplicateFilter_32
    INPUT_ORDERED_CHOICE = No
    KEYATTR = fme_basename
    UNIQUE -> Tester_134
    UNIQUE -> Tester_101
Note: Vytáhne vícelisté výkresy
Tester_134
    BOOL_OP = OR
    TEST_CLAUSE = TEST @Value(_list{2}) > 00
    TEST_MODE = TEST
    PASSED -> AttributeCreator_72
AttributeCreator_72
    ATTR_TABLE:
      SET_TO archivni_cislo = @Value(_list{1})
      SET_TO list = @Value(_list{2})
    -> Tester_135
Tester_135
    BOOL_OP = OR
    TEST_CLAUSE = TEST @Value(list) = 01
    TEST_MODE = TEST
    PASSED -> FeatureMerger_29 [REQUESTOR]
    FAILED -> FeatureMerger_29 [SUPPLIER]
FeatureMerger_29
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(archivni_cislo) @Value(archivni_cislo) AUTO
    MERGE_TYPE = Attributes Only
    PROCESS_DUPS = YES
    REJECT_NULL_MISSING_KEYS = No
    SUPPLIERS_FIRST = No
    UNUSED_SUPPLIER -> AttributeCreator_73
Note: 2V
AttributeCreator_73
    ATTR_TABLE:
      SET_TO KONTROLA = 2V
      SET_TO POPIS = Výkres byl předán bez titulního listu.
      SET_TO DOKUMENTACE = @Value(fme_basename).dwg
    -> Junction_4
Note: TYP_VYKR / VNES / VNIS / JEPS / LINS
Tester_101
    BOOL_OP = OR
    TEST_CLAUSE:
      TEST @Value(TYP_VYKR) = VNES
      TEST @Value(TYP_VYKR) = VNIS
      TEST @Value(TYP_VYKR) = JEPS
      TEST @Value(TYP_VYKR) = LINS
    TEST_MODE = TEST
    PASSED -> FeatureMerger_23 [SUPPLIER]
0 (reader ACAD_1)
    -> AttributeSplitter_22
AttributeSplitter_22
    ATTR_NAME = fme_basename
    DELIMITER = +
    DROP_EMPTY_PARTS = No
    LIST_NAME = _list
    TRIM_OPTION = Both
    -> Tester_88
Note: Kontrolujeme pouze nové výkresy
Tester_88
    BOOL_OP = OR
    TEST_CLAUSE = TEST @Value(_list{3}) = 0
    TEST_MODE = TEST
    PASSED -> DuplicateFilter_18
    PASSED -> Tester_118
    PASSED -> Junction_3
Note: existuje blok
Tester_118
    BOOL_OP = OR
    TEST_CLAUSE = TEST autocad_block_name ATTRIBUTE_HAS_A_VALUE ""
    TEST_MODE = TEST
    PASSED -> DuplicateFilter_9
DuplicateFilter_9
    INPUT_ORDERED_CHOICE = No
    KEYATTR = autocad_block_name fme_basename autocad_extmin_x autocad_extmin_y autocad_extmin_z
    UNIQUE -> FeatureMerger_23 [REQUESTOR]
FeatureMerger_23
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(fme_basename) @Value(fme_basename) AUTO
    MERGE_TYPE = Attributes Only
    PROCESS_DUPS = YES
    REJECT_NULL_MISSING_KEYS = No
    SUPPLIERS_FIRST = No
    MERGED -> AttributeRemover_38
Note: Odstraní nepotřebné
AttributeRemover_38
    REMOVE_ATTRS = autocad_block_number,autocad_color,autocad_extmax_x,autocad_extmax_y,autocad_extmin_x,autocad_extmin_y,autocad_extmin_z,autocad_fillmode,autocad_font_typeface,autocad_insunits,autocad_layout_limit_min_x,autocad_layout_limit_min_y,autocad_layout_name,autocad_linetype,autocad_original_entity_type,autocad_proxygraphics,autocad_scale,autocad_space,autocad_text_size,autocad_viewport_grid_increment_x,autocad_viewport_grid_increment_y,autocad_viewport_snap_angle,autocad_viewport_snap_base_point_x,autocad_viewport_snap_base_point_y,autocad_viewport_snap_increment_x,autocad_viewport_snap_increment_y,autocad_viewport_snap_iso_pair,autocad_viewport_snap_isometric,autocad_width_factor,autocad_xscale,autocad_yscale,autocad_zscale,fme_feature_type,fme_geometry,fme_text_size,INDEX,INDEX-K,JMENO,KONTROLOVAL,LIST,LIST_N,MERITKO,NAZEV_1,NAZEV_2,NAZEV_CASTI,NAZEV_N,POPIS,POPIS_1,POPIS_2,REZERVA1,REZERVA2,REZERVA3,REZERVA_1,REZERVA_2,REZERVA_3,SCHVALIL,SO_DPS,TPO,VYPRACOVAL,ARCH_C,BALIK,CIS_ZM,DATUM,autocad_elevation,autocad_text_string
    -> Tester_100
Note: Autocad_block_name
Tester_100
    BOOL_OP = OR
    TEST_CLAUSE = TEST autocad_block_name ATTRIBUTE_HAS_A_VALUE ""
    TEST_MODE = TEST
    PASSED -> BoundsExtractor
Note: Vytáhne rozložené pozice bloku
BoundsExtractor
    XMIN = _xmin
    YMIN = _ymin
    ZMIN = _zmin
    -> Tester_117
Note: BEZ autocad_layout a viewport
Tester_117
    BOOL_OP = COMPOSITE
    COMPOSITE_TEST = 1 AND 2
    TEST_CLAUSE:
      TEST @Value(autocad_entity) != autocad_layout
      TEST @Value(autocad_entity) != autocad_viewport
    TEST_MODE = TEST
    PASSED -> Tester_119
Note: Odstraní bloky, které jsou anonymní systémově
Tester_119
    BOOL_OP = OR
    TEST_CLAUSE:
      TEST @Value(autocad_block_name) CONTAINS \
      TEST @Value(autocad_block_name) CONTAINS <
      TEST @Value(autocad_block_name) CONTAINS >
      TEST @Value(autocad_block_name) CONTAINS /
      TEST @Value(autocad_block_name) CONTAINS ?
      TEST @Value(autocad_block_name) CONTAINS "
      TEST @Value(autocad_block_name) CONTAINS :
      TEST @Value(autocad_block_name) CONTAINS ;
      TEST @Value(autocad_block_name) CONTAINS *
      TEST @Value(autocad_block_name) CONTAINS ,
      TEST @Value(autocad_block_name) CONTAINS =
      TEST @Value(autocad_block_name) CONTAINS ’
      TEST @Value(autocad_block_name) CONTAINS |
    TEST_MODE = PER_TEST
    FAILED -> AttributeRounder_3
AttributeRounder_3
    PLACES = 6
    ROUND_TYPE = Nearest
    SRC_ATTRS = _xmin _ymin
    -> Tester_98
Tester_98
    BOOL_OP = OR
    TEST_CLAUSE:
      CASE_INSENSITIVE_TEST @Value(_xmin) CONTAINS .
      CASE_INSENSITIVE_TEST @Value(_ymin) CONTAINS .
      CASE_INSENSITIVE_TEST @Value(_zmin) CONTAINS .
    TEST_MODE = PER_TEST
    PASSED -> AttributeSplitter_23
    PASSED -> AttributeSplitter_24
AttributeSplitter_23
    ATTR_NAME = _xmin
    DELIMITER = .
    DROP_EMPTY_PARTS = No
    LIST_NAME = _listx
    TRIM_OPTION = Both
    -> AttributeCreator_39
AttributeCreator_39
    ATTR_TABLE = SET_TO xmin = @Value(_listx{1})
    -> Tester_114
Tester_114
    BOOL_OP = OR
    TEST_CLAUSE = TEST xmin ATTRIBUTE_HAS_A_VALUE ""
    TEST_MODE = TEST
    PASSED -> Tester_103
Tester_103
    BOOL_OP = OR
    TEST_CLAUSE:
      TEST @Value(xmin) = 5
      TEST @Value(xmin) = 000001
    TEST_MODE = TEST
    FAILED -> DuplicateFilter_29
DuplicateFilter_29
    INPUT_ORDERED_CHOICE = No
    KEYATTR = _xmin _ymin autocad_block_name fme_basename
    UNIQUE -> Tester_120
Tester_120
    BOOL_OP = OR
    TEST_CLAUSE:
      TEST @Value(xmin) = 000001
      TEST @Value(xmin) = 500001
      TEST @Value(xmin) = 499998
      TEST @Value(xmin) = 999998
      TEST @Value(xmin) = 999999
    TEST_MODE = TEST
    FAILED -> DuplicateFilter_31
AttributeSplitter_24
    ATTR_NAME = _ymin
    DELIMITER = .
    DROP_EMPTY_PARTS = No
    LIST_NAME = _listy
    TRIM_OPTION = Both
    -> AttributeCreator_60
AttributeCreator_60
    ATTR_TABLE = SET_TO ymin = @Value(_listy{1})
    -> Tester_113
Tester_113
    BOOL_OP = OR
    TEST_CLAUSE = TEST ymin ATTRIBUTE_HAS_A_VALUE ""
    TEST_MODE = TEST
    PASSED -> Tester_107
Tester_107
    BOOL_OP = OR
    TEST_CLAUSE:
      TEST @Value(ymin) = 5
      TEST @Value(ymin) = 000001
    TEST_MODE = TEST
    FAILED -> DuplicateFilter_30
DuplicateFilter_30
    INPUT_ORDERED_CHOICE = No
    KEYATTR = _xmin _ymin autocad_block_name fme_basename
    UNIQUE -> Tester_121
Tester_121
    BOOL_OP = OR
    TEST_CLAUSE:
      TEST @Value(ymin) = 000001
      TEST @Value(ymin) = 500001
      TEST @Value(ymin) = 499998
      TEST @Value(ymin) = 999998
      TEST @Value(ymin) = 999999
    TEST_MODE = TEST
    FAILED -> DuplicateFilter_31
DuplicateFilter_31
    INPUT_ORDERED_CHOICE = No
    KEYATTR = _xmin _ymin autocad_block_name fme_basename
    UNIQUE -> AttributeCreator_61
Note: 3V
AttributeCreator_61
    ATTR_TABLE:
      SET_TO KONTROLA = 3V
      SET_TO POPIS = Pozice bloku @Value(autocad_block_name) (@Value(_xmin), @Value(_ymin), @Value(_zmin)) neodpovídá zadané toleranci.
      SET_TO DOKUMENTACE = @Value(fme_basename).dwg
    -> Junction_4
Note: Hladina 0 musí být prázdná - Vvrací výkresy, které mají geometry v hladině 0
DuplicateFilter_18
    INPUT_ORDERED_CHOICE = No
    KEYATTR = fme_basename autocad_layer
    UNIQUE -> Tester_73
Note: ENTITA_ Autocad_INFO
Tester_73
    BOOL_OP = OR
    TEST_CLAUSE:
      TEST @Value(autocad_entity) = autocad_info
      TEST @Value(autocad_entity) = autocad_line
      TEST @Value(autocad_entity) = autocad_multi_text
      TEST @Value(autocad_entity) = autocad_ellipse
    TEST_MODE = TEST
    FAILED -> Tester_31
Note: BEZ autocad_layout a viewport
Tester_31
    BOOL_OP = COMPOSITE
    COMPOSITE_TEST = 1 AND 2
    TEST_CLAUSE:
      TEST @Value(autocad_entity) != autocad_layout
      TEST @Value(autocad_entity) != autocad_viewport
    TEST_MODE = TEST
    PASSED -> Tester_23
Note: autocad_layer = 0 / fme_geometry != 0
Tester_23
    BOOL_OP = AND
    TEST_CLAUSE:
      TEST @Value(autocad_original_layer) = 0
      TEST @Value(fme_geometry) != null
      TEST @Value(autocad_entity) NOT_= autocad_attr_def
    TEST_MODE = TEST
    PASSED -> AttributeCreator_56
    FAILED -> Tester_97
Tester_97
    BOOL_OP = OR
    TEST_CLAUSE = TEST @Value(fme_feature_type) = 0
    TEST_MODE = TEST
    PASSED -> AttributeCreator_56
Note: 4V
AttributeCreator_56
    ATTR_TABLE:
      SET_TO KONTROLA = 4V
      SET_TO POPIS = Hladina 0 ve výkrese musí být prázdná.
      SET_TO DOKUMENTACE = @Value(fme_basename)
    -> Junction_4
Junction_3
    -> DuplicateFilter_13
    -> Tester_144
    -> Tester_115
    -> Tester_55
    -> Tester_90
    -> DuplicateFilter_12
    -> DuplicateFilter_8

Bookmark: třetí pozice - 1 - Vytvoření kvůli kontrole čísla změny u správného indexu
CharacterCodeExtractor
    CODE_ATTR = _code
    SRC_ATTR = _list{3}
    -> AttributeManager_5
AttributeManager_5
    ATTR_TABLE = SET_TO _code = @Evaluate(@Value(_code)-1)
    USER_EXPOSED_ATTRIBUTES = OZNACENI_INDEX,RUSENE_POZICE,KTD,LOKALITA,POR_C,RUS_ZN,SKRYTE_OZNACENI,TYP_PODTYP,VYPSANE_OZNACENI,autocad_block_name,autocad_layer
    -> CharacterCodeReplacer
CharacterCodeReplacer
    CODE_VAL = @Value(_code)
    STRING_ATTR = _encoded
    -> Tester_74

Bookmark: BLOKY
Note: Kontrolní program - (Kontrolní program DATA_Vykres - kopie (4))
List1 (reader XLSXR_1)
    attributes: ATTRFILL char(9), BLOKY_DIAGRAMU char(22), BLOKY_ELEKTRO char(22), BLOKY_MAR char(28), BLOKY_STROJNI char(9), POPISOVA_POLE char(11), TABULKY char(7), VYKRESOVE_LISTY char(6), BLOKY_AUTOCADU char(11), BLOCKPOS char(8), BLOCKSCALE char(28), ENV=EXTMIN char(6), ENV=FILLMODE number(2,0), ENV=SNAPUNIT char(8), ENV=WORLDUCS number(2,0), LAYER char(27), LAYERNAME char(11), LAYERNAME2 string, LINETYPE char(13), SPACE string, TEXTFONT char(13), TEXTHEIGHT number(7,1), TYPVYKR char(8), TEXTSLOPE number(3,1), TEXTWIDTH2 number(4,1)
    -> AttributeRemover_20
    -> AttributeRemover_21
    -> AttributeRemover_22
    -> AttributeRemover_23
    -> AttributeRemover_24
    -> AttributeRemover_25
    -> AttributeRemover_27
    -> AttributeRemover_26
    -> AttributeRemover_28
AttributeRemover_28
    REMOVE_ATTRS = ATTRFILL,BLOCKSCALE,ENV=EXTMIN,ENV=FILLMODE,ENV=WORLDUCS,fme_feature_type,LAYER,LAYERNAME,LAYERNAME2,LINETYPE,SPACE,TEXTFONT,TEXTSLOPE,TEXTWIDTH2,ENV=SNAPUNIT,TEXTHEIGHT
    -> Junction_5
Junction_5
    -> Tester_47
    -> Tester_52
    -> Tester_49
    -> Tester_50
    -> Tester_53
    -> Tester_60
    -> Tester_61
    -> Tester_54
    -> Tester_51
    -> Tester_62
Note: POPISOVA_POLE
Tester_47
    BOOL_OP = OR
    TEST_CLAUSE = TEST POPISOVA_POLE ATTRIBUTE_IS_MISSING ""
    TEST_MODE = TEST
    FAILED -> AttributeRemover_3
AttributeRemover_3
    REMOVE_ATTRS = BLOCKPOS,BLOKY_AUTOCADU,BLOKY_DIAGRAMU,BLOKY_ELEKTRO,BLOKY_MAR,BLOKY_STROJNI,TABULKY,TYPVYKR,VYKRESOVE_LISTY
    -> AttributeRenamer_6
AttributeRenamer_6
    ATTR_TABLE = RENAME_SET_DEFAULT POPISOVA_POLE > BLOK
    MISSING_INPUT_ATTRS = REMOVE
    -> Junction_2
Note: VYKRESOVE_LISTY
Tester_52
    BOOL_OP = OR
    TEST_CLAUSE = TEST VYKRESOVE_LISTY ATTRIBUTE_IS_MISSING ""
    TEST_MODE = TEST
    FAILED -> AttributeRemover_5
AttributeRemover_5
    REMOVE_ATTRS = BLOCKPOS,BLOKY_AUTOCADU,BLOKY_DIAGRAMU,BLOKY_ELEKTRO,BLOKY_MAR,BLOKY_STROJNI,POPISOVA_POLE,TABULKY,TYPVYKR
    -> AttributeRenamer_14
AttributeRenamer_14
    ATTR_TABLE = RENAME_SET_DEFAULT VYKRESOVE_LISTY > BLOK
    MISSING_INPUT_ATTRS = REMOVE
    -> Junction_2
Note: TABULKY
Tester_49
    BOOL_OP = OR
    TEST_CLAUSE = TEST TABULKY ATTRIBUTE_IS_MISSING ""
    TEST_MODE = TEST
    FAILED -> AttributeRemover_7
AttributeRemover_7
    REMOVE_ATTRS = BLOKY_AUTOCADU,BLOKY_DIAGRAMU,BLOKY_ELEKTRO,BLOKY_MAR,BLOKY_STROJNI,POPISOVA_POLE,TYPVYKR,VYKRESOVE_LISTY,BLOCKPOS
    -> AttributeRenamer_15
AttributeRenamer_15
    ATTR_TABLE = RENAME_SET_DEFAULT TABULKY > BLOK
    MISSING_INPUT_ATTRS = REMOVE
    -> Junction_2
Note: BLOKY_AUTOCADU
Tester_50
    BOOL_OP = OR
    TEST_CLAUSE = TEST BLOKY_AUTOCADU ATTRIBUTE_IS_MISSING ""
    TEST_MODE = TEST
    FAILED -> AttributeRemover_8
AttributeRemover_8
    REMOVE_ATTRS = BLOCKPOS,BLOKY_DIAGRAMU,BLOKY_ELEKTRO,BLOKY_MAR,BLOKY_STROJNI,POPISOVA_POLE,TABULKY,TYPVYKR,VYKRESOVE_LISTY
    -> AttributeRenamer_16
AttributeRenamer_16
    ATTR_TABLE = RENAME_SET_DEFAULT BLOKY_AUTOCADU > BLOK
    MISSING_INPUT_ATTRS = REMOVE
    -> Junction_2
Note: BLOCKPOS
Tester_51
    BOOL_OP = OR
    TEST_CLAUSE = TEST BLOCKPOS ATTRIBUTE_IS_MISSING ""
    TEST_MODE = TEST
    FAILED -> AttributeRemover_9
AttributeRemover_9
    REMOVE_ATTRS = BLOKY_AUTOCADU,BLOKY_DIAGRAMU,BLOKY_ELEKTRO,BLOKY_MAR,BLOKY_STROJNI,POPISOVA_POLE,TABULKY,TYPVYKR,VYKRESOVE_LISTY
    -> AttributeRenamer_17
AttributeRenamer_17
    ATTR_TABLE = RENAME_SET_DEFAULT BLOCKPOS > BLOK
    MISSING_INPUT_ATTRS = REMOVE
    -> Junction_2
Note: BLOKY_DIAGRAMU
Tester_53
    BOOL_OP = OR
    TEST_CLAUSE = TEST BLOKY_DIAGRAMU ATTRIBUTE_IS_MISSING ""
    TEST_MODE = TEST
    FAILED -> AttributeRemover_10
AttributeRemover_10
    REMOVE_ATTRS = BLOCKPOS,BLOKY_AUTOCADU,BLOKY_ELEKTRO,BLOKY_MAR,BLOKY_STROJNI,POPISOVA_POLE,TABULKY,TYPVYKR,VYKRESOVE_LISTY
    -> AttributeRenamer_18
AttributeRenamer_18
    ATTR_TABLE = RENAME_SET_DEFAULT BLOKY_DIAGRAMU > BLOK
    MISSING_INPUT_ATTRS = REMOVE
    -> Junction_2
Note: BLOKY_ELEKTRO
Tester_54
    BOOL_OP = OR
    TEST_CLAUSE = TEST BLOKY_ELEKTRO ATTRIBUTE_IS_MISSING ""
    TEST_MODE = TEST
    FAILED -> AttributeRemover_11
AttributeRemover_11
    REMOVE_ATTRS = BLOCKPOS,BLOKY_AUTOCADU,BLOKY_DIAGRAMU,BLOKY_MAR,BLOKY_STROJNI,POPISOVA_POLE,TABULKY,TYPVYKR,VYKRESOVE_LISTY
    -> AttributeRenamer_19
AttributeRenamer_19
    ATTR_TABLE = RENAME_SET_DEFAULT BLOKY_ELEKTRO > BLOK
    MISSING_INPUT_ATTRS = REMOVE
    -> Junction_2
Note: BLOKY_MAR
Tester_60
    BOOL_OP = OR
    TEST_CLAUSE = TEST BLOKY_MAR ATTRIBUTE_IS_MISSING ""
    TEST_MODE = TEST
    FAILED -> AttributeRemover_12
AttributeRemover_12
    REMOVE_ATTRS = BLOCKPOS,BLOKY_AUTOCADU,BLOKY_DIAGRAMU,BLOKY_ELEKTRO,BLOKY_STROJNI,POPISOVA_POLE,TABULKY,TYPVYKR,VYKRESOVE_LISTY
    -> AttributeRenamer_20
AttributeRenamer_20
    ATTR_TABLE = RENAME_SET_DEFAULT BLOKY_MAR > BLOK
    MISSING_INPUT_ATTRS = REMOVE
    -> Junction_2
Note: BLOKY_STROJNI
Tester_61
    BOOL_OP = OR
    TEST_CLAUSE = TEST BLOKY_STROJNI ATTRIBUTE_IS_MISSING ""
    TEST_MODE = TEST
    FAILED -> AttributeRemover_13
AttributeRemover_13
    REMOVE_ATTRS = BLOCKPOS,BLOKY_AUTOCADU,BLOKY_DIAGRAMU,BLOKY_ELEKTRO,BLOKY_MAR,POPISOVA_POLE,TABULKY,TYPVYKR,VYKRESOVE_LISTY
    -> AttributeRenamer_21
AttributeRenamer_21
    ATTR_TABLE = RENAME_SET_DEFAULT BLOKY_STROJNI > BLOK
    MISSING_INPUT_ATTRS = REMOVE
    -> Junction_2
Note: TYPVYKR
Tester_62
    BOOL_OP = OR
    TEST_CLAUSE = TEST TYPVYKR ATTRIBUTE_IS_MISSING ""
    TEST_MODE = TEST
    FAILED -> AttributeRemover_14
AttributeRemover_14
    REMOVE_ATTRS = BLOCKPOS,BLOKY_AUTOCADU,BLOKY_DIAGRAMU,BLOKY_ELEKTRO,BLOKY_MAR,BLOKY_STROJNI,POPISOVA_POLE,TABULKY,VYKRESOVE_LISTY
    -> AttributeRenamer_22
AttributeRenamer_22
    ATTR_TABLE = RENAME_SET_DEFAULT TYPVYKR > BLOK
    MISSING_INPUT_ATTRS = REMOVE
    -> Junction_2
Junction_2
    -> DuplicateFilter_14
DuplicateFilter_14
    INPUT_ORDERED_CHOICE = No
    KEYATTR = BLOK
    UNIQUE -> FeatureMerger_10 [SUPPLIER]
FeatureMerger_10
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(autocad_block_name) @Value(BLOK) AUTO
    MERGE_TYPE = Attributes Only
    PROCESS_DUPS = YES
    REJECT_NULL_MISSING_KEYS = No
    SUPPLIERS_FIRST = No
    UNMERGED_REQUESTOR -> DuplicateFilter_16
    UNMERGED_REQUESTOR -> FeatureMerger_22 [SUPPLIER]
Note: Autocad_block_name
DuplicateFilter_16
    INPUT_ORDERED_CHOICE = No
    KEYATTR = autocad_source_filename autocad_block_name
    UNIQUE -> AttributeCreator_94
Note: 13V
AttributeCreator_94
    ATTR_TABLE:
      SET_TO KONTROLA = 13V
      SET_TO POPIS = Výkres obsahuje nepovolený blok @Value(autocad_block_name).
      SET_TO DOKUMENTACE = @Value(fme_basename)
    -> Junction_4

Bookmark: Kontrola samostatné hladiny i hladiny v kombinaci s barvou
AttributeRemover_23
    REMOVE_ATTRS = ATTRFILL,BLOCKPOS,BLOCKSCALE,BLOKY_AUTOCADU,BLOKY_DIAGRAMU,BLOKY_ELEKTRO,BLOKY_MAR,BLOKY_STROJNI,ENV=EXTMIN,ENV=FILLMODE,ENV=WORLDUCS,fme_feature_type,LAYER,LAYERNAME2,LINETYPE,POPISOVA_POLE,SPACE,TABULKY,TEXTFONT,TEXTSLOPE,TEXTWIDTH2,TYPVYKR,VYKRESOVE_LISTY,ENV=SNAPUNIT,TEXTHEIGHT
    -> Tester_37
Note: LAYERNAME
Tester_37
    BOOL_OP = OR
    TEST_CLAUSE = TEST LAYERNAME ATTRIBUTE_IS_MISSING ""
    TEST_MODE = TEST
    FAILED -> FeatureMerger_7 [SUPPLIER]
AttributeRemover_24
    REMOVE_ATTRS = ATTRFILL,BLOCKPOS,BLOCKSCALE,BLOKY_AUTOCADU,BLOKY_DIAGRAMU,BLOKY_ELEKTRO,BLOKY_MAR,BLOKY_STROJNI,ENV=EXTMIN,ENV=FILLMODE,ENV=WORLDUCS,fme_feature_type,LAYERNAME,LAYERNAME2,LINETYPE,POPISOVA_POLE,SPACE,TABULKY,TEXTFONT,TEXTSLOPE,TEXTWIDTH2,TYPVYKR,VYKRESOVE_LISTY,ENV=SNAPUNIT,TEXTHEIGHT
    -> Tester_43
Note: LAYER
Tester_43
    BOOL_OP = OR
    TEST_CLAUSE = TEST LAYER ATTRIBUTE_IS_MISSING ""
    TEST_MODE = TEST
    FAILED -> StringSearcher_7
StringSearcher_7
    CASE = no
    MATCHED_RESULT_ATTR = layer_reg
    REGEXP = (?<=\").+?(?=\")
    STRING_TO_SEARCH = @Value(LAYER)
    MATCHED -> StringSearcher_8
StringSearcher_8
    CASE = no
    MATCHED_RESULT_ATTR = layer_color_reg
    REGEXP = [^=]*$
    STRING_TO_SEARCH = @Value(LAYER)
    MATCHED -> FeatureMerger_8 [SUPPLIER]
Tester_115
    BOOL_OP = OR
    TEST_CLAUSE = TEST autocad_layer ATTRIBUTE_HAS_A_VALUE ""
    TEST_MODE = TEST
    PASSED -> DuplicateFilter_7
DuplicateFilter_7
    INPUT_ORDERED_CHOICE = No
    KEYATTR = fme_basename autocad_original_color autocad_layer
    UNIQUE -> Tester_106
Note: BEZ autocad_layout a info
Tester_106
    BOOL_OP = COMPOSITE
    COMPOSITE_TEST = 1 AND 2
    TEST_CLAUSE:
      TEST @Value(autocad_entity) NOT_= autocad_layout
      TEST @Value(autocad_entity) NOT_= autocad_info
    TEST_MODE = TEST
    PASSED -> StringCaseChanger_14
Note: Pro kontrolu hladin
StringCaseChanger_14
    ATTRCHOICE = Selected Attributes
    ATTRLIST = autocad_block_name autocad_original_color autocad_layer
    CHANGE_TYPE = UPPERCASE
    -> Tester_89
Note: Neřešit hladinu 0 a DEFFPOINTS
Tester_89
    BOOL_OP = COMPOSITE
    COMPOSITE_TEST = 1 AND 2
    TEST_CLAUSE:
      TEST @Value(autocad_layer) NOT_= 0
      TEST @UpperCase(@Value(autocad_layer)) NOT_= DEFPOINTS
    TEST_MODE = TEST
    PASSED -> Tester_30
Tester_30
    BOOL_OP = OR
    TEST_CLAUSE = TEST @Value(autocad_entity) NOT_= autocad_hatch
    TEST_MODE = TEST
    PASSED -> Tester_28
    PASSED -> FeatureMerger_7 [REQUESTOR]
FeatureMerger_7
    ATTR_ACCUM_MODE = Merge Supplier
    ATTR_CONFLICT_RES = Use Requestor
    IGNORE_NULLS = No
    JOIN_KEYS = @Value(autocad_layer) @Value(LAYERNAME) AUTO
    MERGE_TYPE = Attributes Only
    PROCESS_DUPS = NO
    REJECT_NULL_MISSING_KEYS = No
    SUPPLIERS_FIRST = No
    UNMERGED_REQUESTOR -> FeatureMerger_20 [SUPPLIER]
    UNMERGED_REQUESTOR -> AttributeCreator_88
Note: 5V
AttributeCreator_88
    ATTR_TABLE:
      SET_TO KONTROLA = 5V
      SET_TO POPIS = Výkres obsahuje nepovolenou hladinu "@Value(autocad_layer)".
      SET_TO DOKUMENTACE = @Value(fme_basename)
    -> Junction_4
Note: Neřešit hladinu 0 a DEFFPOINTS
Tester_28
    BOOL_OP = COMPOSITE
    COMPOSITE_TEST = 1 AND 2
    TEST_CLAUSE:
      TEST @Value(autocad_original_color) NOT_= BYBLOCK
      TEST @Value(autocad_original_color) NOT_= BYLAYER
    TEST_MODE = TEST
    PASSED -> FeatureMerger_8 [REQUESTOR]
FeatureMerger_8
    ATTR_ACCUM_MODE = Merge Supplier
    ATTR_CONFLICT_RES = Use Requestor
    IGNORE_NULLS = No
    JOIN_KEYS = @Value(autocad_layer) @Value(layer_reg) AUTO @Value(autocad_original_color) @Value(layer_color_reg) AUTO
    MERGE_TYPE = Attributes Only
    PROCESS_DUPS = NO
    REJECT_NULL_MISSING_KEYS = No
    SUPPLIERS_FIRST = No
    UNMERGED_REQUESTOR -> FeatureMerger_20 [REQUESTOR]
Note: Odebere hladiny, které nejsou povoleny
FeatureMerger_20
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(fme_basename) @Value(fme_basename) AUTO @Value(autocad_layer) @Value(autocad_layer) AUTO
    MERGE_TYPE = Attributes Only
    PROCESS_DUPS = YES
    REJECT_NULL_MISSING_KEYS = No
    SUPPLIERS_FIRST = No
    UNMERGED_REQUESTOR -> FeatureMerger_22 [REQUESTOR]
Note: Odebere bloky, které nejsou povoleny
FeatureMerger_22
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(fme_basename) @Value(fme_basename) AUTO @Value(autocad_block_name) @Value(autocad_block_name) AUTO
    MERGE_TYPE = Attributes Only
    PROCESS_DUPS = YES
    REJECT_NULL_MISSING_KEYS = No
    SUPPLIERS_FIRST = No
    UNMERGED_REQUESTOR -> AttributeCreator_89
Note: 6V
AttributeCreator_89
    ATTR_TABLE:
      SET_TO KONTROLA = 6V
      SET_TO POPIS = Výkres obsahuje nepovolenou kombinaci hladiny "@Value(autocad_layer)" a barvy "@Value(autocad_original_color)".
      SET_TO DOKUMENTACE = @Value(fme_basename)
    -> Junction_4

Bookmark: Nepovolený typ čáry
AttributeRemover_22
    REMOVE_ATTRS = ATTRFILL,BLOCKPOS,BLOCKSCALE,BLOKY_AUTOCADU,BLOKY_DIAGRAMU,BLOKY_ELEKTRO,BLOKY_MAR,BLOKY_STROJNI,ENV=EXTMIN,ENV=FILLMODE,ENV=WORLDUCS,fme_feature_type,LAYER,LAYERNAME,LAYERNAME2,POPISOVA_POLE,SPACE,TABULKY,TEXTFONT,TEXTSLOPE,TEXTWIDTH2,TYPVYKR,VYKRESOVE_LISTY,ENV=SNAPUNIT,TEXTHEIGHT
    -> Tester_41
Note: LINETYPE
Tester_41
    BOOL_OP = OR
    TEST_CLAUSE = TEST LINETYPE ATTRIBUTE_IS_MISSING ""
    TEST_MODE = TEST
    FAILED -> FeatureMerger_6 [SUPPLIER]
Tester_144
    BOOL_OP = OR
    TEST_CLAUSE = TEST autocad_linetype ATTRIBUTE_HAS_A_VALUE ""
    TEST_MODE = TEST
    PASSED -> DuplicateFilter_10
Note: Autocad_linetype
DuplicateFilter_10
    INPUT_ORDERED_CHOICE = No
    KEYATTR = autocad_source_filename autocad_linetype
    UNIQUE -> Tester_38
Note: BEZ autocad_layout a info
Tester_38
    BOOL_OP = AND
    TEST_CLAUSE:
      TEST @Value(autocad_entity) != autocad_layout
      TEST @Value(autocad_entity) != autocad_info
    TEST_MODE = TEST
    PASSED -> StringCaseChanger_6
Note: Pro kontrolu typu čar / autocad_linetype
StringCaseChanger_6
    ATTRCHOICE = Selected Attributes
    ATTRLIST = autocad_linetype
    CHANGE_TYPE = UPPERCASE
    -> FeatureMerger_6 [REQUESTOR]
FeatureMerger_6
    ATTR_ACCUM_MODE = Merge Supplier
    ATTR_CONFLICT_RES = Use Requestor
    IGNORE_NULLS = No
    JOIN_KEYS = @Value(autocad_linetype) @Value(LINETYPE) AUTO
    MERGE_TYPE = Attributes Only
    PROCESS_DUPS = NO
    REJECT_NULL_MISSING_KEYS = No
    SUPPLIERS_FIRST = No
    UNMERGED_REQUESTOR -> AttributeCreator_85
Note: 7V
AttributeCreator_85
    ATTR_TABLE:
      SET_TO KONTROLA = 7V
      SET_TO POPIS = Nepovolený typ čáry "@Value(autocad_linetype)".
      SET_TO DOKUMENTACE = @Value(fme_basename)
    -> Junction_4

Bookmark: Nepovolený font
AttributeRemover_21
    REMOVE_ATTRS = ATTRFILL,BLOCKPOS,BLOCKSCALE,BLOKY_AUTOCADU,BLOKY_DIAGRAMU,BLOKY_ELEKTRO,BLOKY_MAR,BLOKY_STROJNI,ENV=EXTMIN,ENV=FILLMODE,ENV=WORLDUCS,fme_feature_type,LAYER,LAYERNAME,LAYERNAME2,LINETYPE,POPISOVA_POLE,SPACE,TABULKY,TEXTSLOPE,TEXTWIDTH2,TYPVYKR,VYKRESOVE_LISTY,ENV=SNAPUNIT,TEXTHEIGHT
    -> Tester_40
Note: TEXTFONT
Tester_40
    BOOL_OP = OR
    TEST_CLAUSE = TEST TEXTFONT ATTRIBUTE_IS_MISSING ""
    TEST_MODE = TEST
    FAILED -> StringSearcher_6
Note: oddělení přípony
StringSearcher_6
    CASE = no
    MATCHED_RESULT_ATTR = _first_match
    REGEXP = .*(?=\.)
    STRING_TO_SEARCH = @Value(TEXTFONT)
    MATCHED -> StringCaseChanger_13
StringCaseChanger_13
    ATTRCHOICE = Selected Attributes
    ATTRLIST = _first_match
    CHANGE_TYPE = UPPERCASE
    -> FeatureJoiner_7 [RIGHT]
Note: TextFont
Tester_90
    BOOL_OP = OR
    TEST_CLAUSE = TEST autocad_font_typeface ATTRIBUTE_HAS_A_VALUE ""
    TEST_MODE = TEST
    PASSED -> DuplicateFilter_11
DuplicateFilter_11
    INPUT_ORDERED_CHOICE = No
    KEYATTR = autocad_font_typeface fme_basename
    UNIQUE -> FeatureJoiner_7 [LEFT]
FeatureJoiner_7
    ATTR_CONFLICT_RES = Use Left
    GEOMETRY_HANDLING = Use Left
    JOIN_KEYS = autocad_font_typeface _first_match AUTO
    JOIN_MODE = Inner
    UNJOINED_LEFT -> AttributeCreator_87
Note: 8V
AttributeCreator_87
    ATTR_TABLE:
      SET_TO KONTROLA = 8V
      SET_TO POPIS = Nepovolený font "@Value(autocad_font_typeface)".
      SET_TO DOKUMENTACE = @Value(fme_basename)
    -> Junction_4

Bookmark: Výška textu
AttributeRemover_20
    REMOVE_ATTRS = ATTRFILL,BLOCKPOS,BLOCKSCALE,BLOKY_AUTOCADU,BLOKY_DIAGRAMU,BLOKY_ELEKTRO,BLOKY_MAR,BLOKY_STROJNI,ENV=EXTMIN,ENV=FILLMODE,ENV=WORLDUCS,fme_feature_type,LAYER,LAYERNAME,LAYERNAME2,LINETYPE,POPISOVA_POLE,SPACE,TABULKY,TEXTFONT,TEXTSLOPE,TEXTWIDTH2,TYPVYKR,VYKRESOVE_LISTY,ENV=SNAPUNIT
    -> Tester_39
Note: TEXTHEIGHT
Tester_39
    BOOL_OP = OR
    TEST_CLAUSE = TEST TEXTHEIGHT ATTRIBUTE_IS_MISSING ""
    TEST_MODE = TEST
    FAILED -> FeatureMerger_21 [SUPPLIER]
Note: Autocad_text_size
DuplicateFilter_8
    INPUT_ORDERED_CHOICE = No
    KEYATTR = autocad_text_size fme_basename fme_text_size
    UNIQUE -> Tester_104
Note: BEZ autocad_layout a viewport
Tester_104
    BOOL_OP = COMPOSITE
    COMPOSITE_TEST = 1 AND 2
    TEST_CLAUSE:
      TEST @Value(autocad_entity) != autocad_layout
      TEST @Value(autocad_entity) != autocad_viewport
    TEST_MODE = TEST
    PASSED -> Tester_105
Note: autocad_layer = 0 / fme_geometry != 0
Tester_105
    BOOL_OP = COMPOSITE
    COMPOSITE_TEST = 1 AND 2
    TEST_CLAUSE:
      TEST @Value(autocad_layer) = 0
      TEST @Value(fme_geometry) != null
    TEST_MODE = TEST
    PASSED -> Tester_33
Note: autocad_entity = text
Tester_33
    BOOL_OP = OR
    TEST_CLAUSE = TEST @Value(autocad_entity) = autocad_text
    TEST_MODE = TEST
    PASSED -> Tester_99
Note: Vyfiltruje hodnoty menší než 1.8 - ty jsou rovnou chybové
Tester_99
    BOOL_OP = OR
    TEST_CLAUSE = TEST @Value(fme_text_size) < 1.8
    TEST_MODE = TEST
    PASSED -> AttributeCreator_66
    FAILED -> AttributeRounder
Note: Pro kontrolu velikosti písma / dle kontrolního programu
AttributeRounder
    PLACES = 6
    ROUND_TYPE = Nearest
    SRC_ATTRS = autocad_text_size
    -> FeatureMerger_21 [REQUESTOR]
FeatureMerger_21
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(fme_text_size) @Value(TEXTHEIGHT) AUTO
    MERGE_TYPE = Attributes Only
    PROCESS_DUPS = YES
    REJECT_NULL_MISSING_KEYS = No
    SUPPLIERS_FIRST = No
    UNMERGED_REQUESTOR -> AttributeCreator_66
Note: 9V
AttributeCreator_66
    ATTR_TABLE:
      SET_TO KONTROLA = 9V
      SET_TO POPIS = Nepovolená výška textu "@Value(autocad_text_size)".
      SET_TO DOKUMENTACE = @Value(fme_basename)
    -> Junction_4

Bookmark: Systémová proměnná FILLMODE
AttributeRemover_25
    REMOVE_ATTRS = ATTRFILL,BLOCKPOS,BLOCKSCALE,BLOKY_AUTOCADU,BLOKY_DIAGRAMU,BLOKY_ELEKTRO,BLOKY_MAR,BLOKY_STROJNI,ENV=EXTMIN,ENV=WORLDUCS,fme_feature_type,LAYER,LAYERNAME,LAYERNAME2,LINETYPE,POPISOVA_POLE,SPACE,TABULKY,TEXTFONT,TEXTSLOPE,TEXTWIDTH2,TYPVYKR,VYKRESOVE_LISTY,ENV=SNAPUNIT,TEXTHEIGHT
    -> Tester_46
Note: ENV=FILLMODE
Tester_46
    BOOL_OP = OR
    TEST_CLAUSE = TEST ENV=FILLMODE ATTRIBUTE_IS_MISSING ""
    TEST_MODE = TEST
    FAILED -> AttributeManager_2
Note: Změna podmínkou z 1 na Yes
AttributeManager_2
    ATTR_TABLE = RENAME_SET_DEFAULT env_fillmode_2 = FME_CONDITIONAL:DEFAULT_VALUE'No'BOOL_OP;OR;COMPOSITE_TEST;1;TEST @Value(ENV=FILLMODE) = 1'Yes'FME_NUM_CONDITIONS2___
    USER_EXPOSED_ATTRIBUTES = env_fillmode_2
    -> FeatureMerger_9 [SUPPLIER]
Note: Autocad_fillmode / a / Autocad_fillmode2
DuplicateFilter_13
    INPUT_ORDERED_CHOICE = No
    KEYATTR = autocad_fillmode fme_basename
    UNIQUE -> AttributeRemover_29
AttributeRemover_29
    REMOVE_ATTRS = autocad_block_number,autocad_extmax_x,autocad_extmax_y,autocad_extmin_x,autocad_extmin_y,autocad_extmin_z,autocad_font_typeface,autocad_insunits,autocad_layout_name,autocad_original_entity_type,autocad_proxygraphics,autocad_scale,autocad_space,autocad_text_size,autocad_viewport_grid_increment_x,autocad_viewport_grid_increment_y,autocad_viewport_snap_angle,autocad_viewport_snap_base_point_x,autocad_viewport_snap_base_point_y,autocad_viewport_snap_increment_x,autocad_viewport_snap_increment_y,autocad_viewport_snap_iso_pair,autocad_viewport_snap_isometric,autocad_width_factor,fme_feature_type,fme_geometry,fme_text_size,autocad_block_name,autocad_color,autocad_layer,autocad_linetype,autocad_xscale,autocad_yscale,autocad_zscale
    -> Tester_45
Note: autocad_info
Tester_45
    BOOL_OP = OR
    TEST_CLAUSE = TEST @Value(autocad_entity) = autocad_info
    TEST_MODE = TEST
    PASSED -> FeatureMerger_9 [REQUESTOR]
FeatureMerger_9
    ATTR_ACCUM_MODE = Merge Supplier
    ATTR_CONFLICT_RES = Use Requestor
    IGNORE_NULLS = No
    JOIN_KEYS = @Value(autocad_fillmode) @Value(env_fillmode_2) AUTO
    MERGE_TYPE = Attributes Only
    PROCESS_DUPS = NO
    REJECT_NULL_MISSING_KEYS = No
    SUPPLIERS_FIRST = No
    UNMERGED_REQUESTOR -> AttributeCreator_90
Note: 10V
AttributeCreator_90
    ATTR_TABLE:
      SET_TO KONTROLA = 10V
      SET_TO POPIS = Obsahuje nepovolené hodnoty systémové proměnné (fillmode) "@Value(autocad_fillmode)".
      SET_TO DOKUMENTACE = @Value(fme_basename)
    -> Junction_4

Bookmark: Šírka textu
AttributeRemover_26
    REMOVE_ATTRS = ATTRFILL,BLOCKPOS,BLOCKSCALE,BLOKY_AUTOCADU,BLOKY_DIAGRAMU,BLOKY_ELEKTRO,BLOKY_MAR,BLOKY_STROJNI,ENV=EXTMIN,ENV=FILLMODE,ENV=WORLDUCS,fme_feature_type,LAYER,LAYERNAME,LAYERNAME2,LINETYPE,POPISOVA_POLE,SPACE,TABULKY,TEXTFONT,TEXTSLOPE,TYPVYKR,VYKRESOVE_LISTY,ENV=SNAPUNIT,TEXTHEIGHT
    -> Tester_58
Note: TEXTWIDTH2
Tester_58
    BOOL_OP = OR
    TEST_CLAUSE = TEST TEXTWIDTH2 ATTRIBUTE_IS_MISSING ""
    TEST_MODE = TEST
    FAILED -> FeatureMerger_15 [SUPPLIER]
DuplicateFilter_12
    INPUT_ORDERED_CHOICE = No
    KEYATTR = autocad_width_factor fme_basename
    UNIQUE -> Tester_36
Note: Autocad_width_factor má hodnotu
Tester_36
    BOOL_OP = OR
    TEST_CLAUSE = TEST autocad_width_factor ATTRIBUTE_HAS_A_VALUE ""
    TEST_MODE = TEST
    PASSED -> Tester_57
Note: autocad_entity = autocad_text
Tester_57
    BOOL_OP = OR
    TEST_CLAUSE = TEST @Value(autocad_entity) = autocad_text
    TEST_MODE = TEST
    PASSED -> AttributeSplitter_11
Note: Autocad_width_factor
AttributeSplitter_11
    ATTR_NAME = autocad_width_factor
    DELIMITER = 00
    DROP_EMPTY_PARTS = No
    LIST_NAME = _list_
    TRIM_OPTION = Both
    -> AttributeCreator_27
Note: Zaokrouhlování, protože 0.,699 nebereme jako chybu. Berou se až vyšší odchylky.
AttributeCreator_27
    ATTR_TABLE = SET_TO Zaokrouhleno = @Value(_list_{0})
    -> FeatureMerger_15 [REQUESTOR]
Note: autocad_width_factor / a / TEXTWIDTH2
FeatureMerger_15
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(Zaokrouhleno) @Value(TEXTWIDTH2) AUTO
    MERGE_TYPE = Attributes Only
    PROCESS_DUPS = YES
    REJECT_NULL_MISSING_KEYS = No
    SUPPLIERS_FIRST = No
    UNMERGED_REQUESTOR -> AttributeCreator_91
Note: 11V
AttributeCreator_91
    ATTR_TABLE:
      SET_TO KONTROLA = 11V
      SET_TO POPIS = Nepovolená šířka textu @Value(autocad_width_factor).
      SET_TO DOKUMENTACE = @Value(fme_basename)
    -> Junction_4

Bookmark: Nepovolené měřítko
AttributeRemover_27
    REMOVE_ATTRS = ATTRFILL,BLOCKPOS,BLOKY_AUTOCADU,BLOKY_DIAGRAMU,BLOKY_ELEKTRO,BLOKY_MAR,BLOKY_STROJNI,ENV=EXTMIN,ENV=FILLMODE,ENV=WORLDUCS,fme_feature_type,LAYER,LAYERNAME,LAYERNAME2,LINETYPE,POPISOVA_POLE,SPACE,TABULKY,TEXTFONT,TEXTSLOPE,TEXTWIDTH2,TYPVYKR,VYKRESOVE_LISTY,ENV=SNAPUNIT,TEXTHEIGHT
    -> Tester_56
Note: BLOCKSCALE / Měřítko bloku
Tester_56
    BOOL_OP = OR
    TEST_CLAUSE = TEST BLOCKSCALE ATTRIBUTE_IS_MISSING ""
    TEST_MODE = TEST
    FAILED -> FeatureMerger_14 [SUPPLIER]
Note: Autocad_Entity = Autocad_Insert
Tester_55
    BOOL_OP = OR
    TEST_CLAUSE = TEST @Value(autocad_entity) = autocad_insert
    TEST_MODE = TEST
    PASSED -> Tester_68
Note: BEZ bloku na začátku _
Tester_68
    BOOL_OP = OR
    TEST_CLAUSE = CASE_INSENSITIVE_TEST @Value(autocad_block_name) NOT_BEGINS_WITH _
    TEST_MODE = PER_TEST
    PASSED -> AttributeCreator_6
Note: Sloučí BlockScale x, y, z
AttributeCreator_6
    ATTR_TABLE = SET_TO blokscale_xyz = @Value(autocad_xscale),@Value(autocad_yscale),@Value(autocad_zscale)
    -> DuplicateFilter_15
DuplicateFilter_15
    INPUT_ORDERED_CHOICE = No
    KEYATTR = blokscale_xyz autocad_block_name fme_basename
    UNIQUE -> StringCaseChanger_7
Note: všechny bloky z výkresu / UPPERCASE / autocad_block_name
StringCaseChanger_7
    ATTRCHOICE = Selected Attributes
    ATTRLIST = autocad_block_name
    CHANGE_TYPE = UPPERCASE
    -> FeatureMerger_10 [REQUESTOR]
    -> FeatureMerger_14 [REQUESTOR]
FeatureMerger_14
    ATTR_ACCUM_MODE = Merge Supplier
    ATTR_CONFLICT_RES = Use Requestor
    IGNORE_NULLS = No
    JOIN_KEYS = @Value(blokscale_xyz) @Value(BLOCKSCALE) AUTO
    MERGE_TYPE = Attributes Only
    PROCESS_DUPS = NO
    REJECT_NULL_MISSING_KEYS = No
    SUPPLIERS_FIRST = No
    UNMERGED_REQUESTOR -> AttributeCreator_92
Note: 12V
AttributeCreator_92
    ATTR_TABLE:
      SET_TO KONTROLA = 12V
      SET_TO POPIS = Blok @Value(autocad_block_name) nemá požadované měřítko (@Value(blokscale_xyz)).
      SET_TO DOKUMENTACE = @Value(fme_basename)
    -> Junction_4

Bookmark: Výstupní excel chyb
Junction_4
    -> Sorter_2
Note: Seřadí podle názvu dokumentu
Sorter_2
    SORT_PARM = DOKUMENTACE NATURAL ASCENDING
    SORTED -> Tester_143
Note: Podívá se, jestli má / v názvu .dwg a pokud ne, tak přidá přes AttributeCreator
Tester_143
    BOOL_OP = OR
    TEST_CLAUSE = CASE_INSENSITIVE_TEST @Value(fme_basename) CONTAINS .dwg
    TEST_MODE = TEST
    PASSED -> GeometryRemover_3
    FAILED -> AttributeCreator_36
AttributeCreator_36
    ATTR_TABLE = SET_TO DOKUMENTACE = @Value(fme_basename).dwg
    -> GeometryRemover_3
Note: Odstraní geometrii / v dokumentech (tif apod.)
GeometryRemover_3
    -> DuplicateFilter_6
DuplicateFilter_6
    INPUT_ORDERED_CHOICE = No
    KEYATTR = DOKUMENTACE KONTROLA POPIS
    UNIQUE -> DuplicateFilter_17
