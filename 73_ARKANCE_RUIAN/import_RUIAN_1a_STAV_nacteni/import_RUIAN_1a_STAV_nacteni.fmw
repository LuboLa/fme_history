FME workspace import_RUIAN_1a_STAV_nacteni.fmw

Parameters:
- DETAIL_OBCE = NO   # Zpracovat OBCE
- DETAIL_STAT = YES   # Zpracovat STÁT
- RUIAN_SERV = NO   # Vytvořit fulltext pro Ruian Service (PG)
- OBEC = 560812
- ULOZISTE_BALICKU = D:\temp   # Úložiště balíčků VFR
- VFR_DATE = 20230731   # Datum datové sady VFR ve formátu YYYYMMDD
- DB_TYPE = PostgreSQL   # Vyber typ DB
- DestDataset_POSTGRES = PG_FME_RUIAN   # Připojení PostgreSQL
- DestDataset_MSSQL = MSSQL RUIAN   # SQL Server Připojení MSSQL

Writers:
- MSSQL_SPATIAL_2: MSSQL_SPATIAL to $(DestDataset_MSSQL)
- POSTGRES_1: POSTGRES to $(DestDataset_POSTGRES)

Note: Vytvoření dummy
Creator
    GEOMTYPE = Geometry Object
    NUM = 1
    CREATED -> TestFilter_2
    CREATED -> TestFilter_3
    CREATED -> Tester
    CREATED -> Tester_2
Note: promazání databáze - tabulek RN_
TestFilter_2
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> Truncate_verze [INITIATOR]
    PostgreSQL -> Truncate_verze_2 [INITIATOR]
TestFilter_3
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> Disable_indices [INITIATOR]
    PostgreSQL -> Drop_indices [INITIATOR]
Tester_2
    BOOL_OP = OR
    TEST_CLAUSE = TEST $(DETAIL_STAT) = YES
    TEST_MODE = TEST
    PASSED -> HTTPCaller_2
Note: Stažení souborů VFR pro stát
HTTPCaller_2
    CONNECTION_TIMEOUT_LENGTH = 60
    ERROR_ATTR = _error
    FILE_PATH_ATTR = _response_file_path
    FOLLOW_REDIRECTS = FOLLOW_WITH_GET
    HTTP_METHOD = GET
    MAX_HTTP_VERSION = HTTP_2
    MAX_TRANSFERS_IN_PROGRESS = 100
    MINIMUM_ENCRYPTION_LEVEL = OS_DEFAULT
    OUTPUT_FILENAME = $(ULOZISTE_BALICKU)/$(VFR_DATE)_ST_UKSH.xml.zip
    REDIRECT_AUTH = ORIGINAL_DOMAIN_ONLY
    RESPONSE_TYPE = File
    RETRY_FAILED_TRANSFERS = CONNECTION 429 500 501 502 503 504 505 506 507 508 509 510 511
    RETRY_INITIAL_BACKOFF = 1000
    RETRY_MAX_RETRIES = 3
    STATUS_CODE_ATTR = _http_status_code
    TARGET_URL = https://vdp.cuzk.cz/vymenny_format/soucasna/$(VFR_DATE)_ST_UKSH.xml.zip
    TRANSFER_TIMEOUT_LENGTH = 90
    USE_COOKIES = No
    VERIFY_SSL_CERTIFICATES = Yes
    -> FMEServerJobSubmitter
Tester
    BOOL_OP = OR
    TEST_CLAUSE = TEST $(DETAIL_OBCE) = YES
    TEST_MODE = TEST
    PASSED -> ParameterFetcher
Note: Převedení hodnoty paramteru do atributu
ParameterFetcher
    ATTR_LIST = OBEC $(OBEC)
    -> AttributeSplitter
Note: Rozdělení hodnoty atributu do listu
AttributeSplitter
    ATTR_NAME = OBEC
    DELIMITER = " "
    DROP_EMPTY_PARTS = No
    LIST_NAME = _list
    TRIM_OPTION = Both
    -> ListExploder
Note: Rozložení listu do single feature
ListExploder
    ATTR_ACCUM_MODE = Merge List Attributes
    ATTR_CONFLICT_RES = Use List Attribute Values
    LIST_ATTR = _list{}
    ELEMENTS -> HTTPCaller
Note: Stažení souborů VFR pro obce
HTTPCaller
    CONNECTION_TIMEOUT_LENGTH = 60
    ERROR_ATTR = _error
    FILE_PATH_ATTR = _response_file_path
    FOLLOW_REDIRECTS = FOLLOW_WITH_GET
    HTTP_METHOD = GET
    MAX_HTTP_VERSION = HTTP_2
    MAX_TRANSFERS_IN_PROGRESS = 100
    MINIMUM_ENCRYPTION_LEVEL = OS_DEFAULT
    OUTPUT_FILENAME = $(ULOZISTE_BALICKU)/$(VFR_DATE)_OB_@Value(_list)_UKSH.xml.zip
    REDIRECT_AUTH = ORIGINAL_DOMAIN_ONLY
    RESPONSE_TYPE = File
    RETRY_FAILED_TRANSFERS = CONNECTION 429 500 501 502 503 504 505 506 507 508 509 510 511
    RETRY_INITIAL_BACKOFF = 1000
    RETRY_MAX_RETRIES = 3
    STATUS_CODE_ATTR = _http_status_code
    TARGET_URL = https://vdp.cuzk.cz/vymenny_format/soucasna/$(VFR_DATE)_OB_@Value(_list)_UKSH.xml.zip
    TRANSFER_TIMEOUT_LENGTH = 90
    USE_COOKIES = No
    VERIFY_SSL_CERTIFICATES = Yes
    -> FMEServerJobSubmitter
FMEServerJobSubmitter
    ACTION = SUBMIT_JOB
    BLOCKING = FALSE
    PRIORITY = 100 (normal)
Decelerator
    DECEL_TYPE = Per Feature Delay
    DELAY = 20
    -> AttributeManager
Ruian_Service_Fulltext: TestFilter
    DEFAULT_VALUE = <UNFILTERED>
    PASSED_TEST_GROUP_OUTPUT = FIRST
    TEST_LIST = "BOOL_OP,OR,COMPOSITE_TEST,""""""1"""""",TEST_CLAUSE,TEST $(RUIAN_SERV) = YES",Ano
    Ano -> SQLExecutor_3 [INITIATOR]
    <UNFILTERED> -> rn_verze (writer POSTGRES_1)
Note: Generování fulltextu
SQLExecutor_3
    ATTR_IGNORE_NULLS = Yes
    COMBINE_ATTRS = Keep Initiator Attributes if Conflict
    COMBINE_GEOM = Initiator Geometry Only
    DATASET = $(DestDataset_POSTGRES)
    FORMAT = POSTGRES
    OUTPUT_FEATURES_DISPLAY = Data Features
    POSTGRES_CREATE_FEATURE_TABLES_FROM_DATA = Yes
    POSTGRES_NAMED_CONNECTION = $(DestDataset_POSTGRES)
    POSTGRES_QUERY_FEATURE_TYPES_FOR_MERGE_FILTERS = Yes
    POSTGRES_READ_TIME_WITH_TIMEZONE = Yes
    POSTGRES_SCHEMAS_FOR_TABLE_LISTING = ruian
    SQL_STATEMENT:
      --7.8.2020. PP -> MZ
      --19.10.2020 MZ,  úprava generování cislo, + cislo_cp, + cislo_co, cislo jiz neni ve vektoru

      --Provede aktualizaci dat pro fulltextový katalog

      -- Vyprázdnění tabulky
      truncate table ruian.rn_fulltext_adresy;

      -- Restart sekvence
      alter sequence ruian.rn_fulltext_adresy_id_seq RESTART with 1;

      -- Naplnění tabulky adresními místy
      insert into ruian.rn_fulltext_adresy
              (okres_kod,
      		okres_nazev,
      		obec_kod,
      		obec_nazev,
      		cast_obce_kod,
      		cast_obce_nazev,
      		adresa_kod,
      		adresa_psc,
      		ulice_kod,
      		ulice_nazev,
      		cislo,
      		cislo_cp,
      		cislo_co,
      		id,
      		fulltext,
      		rank_boost)
      select	okres_kod,
      		okres_nazev,
      		obec_kod,
      		obec_nazev,
      		cast_obce_kod,
      		cast_obce_nazev,
      		adresa_kod,
      		adresa_psc,
      		ulice_kod,
      		ulice_nazev,
      		REPLACE(cislo, 'budova s ', '') as cislo,
      		cislo_cp,
      		cislo_co,
      		nextval('ruian.rn_fulltext_adresy_id_seq'),
      		REPLACE(fulltext, 'budova s ', '') as fulltext,
      		rank_boost
      		from
      (
      select  distinct
      		ok.KOD OKRES_KOD,
      		ok.NAZEV OKRES_NAZEV,
      		ob.kod OBEC_KOD,
      		ob.nazev OBEC_NAZEV,
      		cob.KOD CAST_OBCE_KOD,
      		cob.NAZEV CAST_OBCE_NAZEV,
      		adr.KOD ADRESA_KOD,
      		adr.adrp_psc ADRESA_PSC,
      		ul.KOD ULICE_KOD,
      		ul.nazev ULICE_NAZEV,
      	(sotyp.short_value || ' ' ||
      (case
        WHEN adr.CISLO_ORIENTACNI_HODNOTA is not null THEN cast(adr.CISLO_DOMOVNI as varchar) || '/' || cast(adr.CISLO_ORIENTACNI_HODNOTA as varchar) || coalesce(adr.CISLO_ORIENTACNI_PISMENO, '')
        else
          cast(adr.CISLO_DOMOVNI as varchar)
      END )) CISLO,
      adr.CISLO_DOMOVNI cislo_cp,
      (case
        WHEN adr.CISLO_ORIENTACNI_HODNOTA is not null THEN cast(adr.CISLO_ORIENTACNI_HODNOTA as varchar) || coalesce(adr.CISLO_ORIENTACNI_PISMENO, '')
        else
          cast(adr.CISLO_ORIENTACNI_PISMENO as varchar)
      END ) cislo_co,
      ((case
      			when ob.nazev <> cob.nazev and ul.nazev is null then (ob.nazev || ' ' || cob.nazev || ' ' )
      			else (ob.nazev || ' ') end) || coalesce(ul.nazev, ' ') || ' ' ||
      		(sotyp.short_value || ' ' ||
      case
        WHEN adr.CISLO_ORIENTACNI_HODNOTA is not null THEN cast(adr.CISLO_DOMOVNI as varchar) || '/' || cast(adr.CISLO_ORIENTACNI_HODNOTA as varchar) || coalesce(adr.CISLO_ORIENTACNI_PISMENO, '')
        else
          cast(adr.CISLO_DOMOVNI as varchar)
      END )) as fulltext,
      1 rank_boost
      from ruian.rn_obec_b ob
      join ruian.rn_cast_obce_b cob on ob.kod = cob.obec_kod
      join ruian.rn_stavebni_objekt_b stav on stav.cobce_kod = cob.kod
      join ruian.rn_adresni_misto_b adr on adr.stavobj_kod = stav.kod
      join ruian.rn_stavebni_objekt_b so on so.kod = adr.stavobj_kod
      join ruian.CS_TYP_STAVEB_OBJEKTU_TBD sotyp on sotyp.id=so.typ_kod
      left join ruian.RN_OKRES_B ok on ob.OKRES_KOD = ok.KOD
      left join ruian.RN_ULICE_L ul on adr.ulice_kod = ul.kod
      ) xx;

      -- (sotyp.short_value || ' ' ||
      -- case
        -- WHEN adr.CISLO_ORIENTACNI_HODNOTA is not null THEN cast(adr.CISLO_DOMOVNI as varchar) || '/' || cast(adr.CISLO_ORIENTACNI_HODNOTA as varchar) || coalesce(adr.CISLO_ORIENTACNI_PISMENO, '')
        -- else
          -- cast(adr.CISLO_DOMOVNI as varchar)
      -- END ) CISLO,


      -- Naplnění tabulky ulicemi
      insert into ruian.rn_fulltext_adresy (okres_kod,
      		okres_nazev,
      		obec_kod,
      		obec_nazev,
      		cast_obce_kod,
      		cast_obce_nazev,
      		ulice_kod,
      		ulice_nazev,
      		ID,
      		fulltext,
      		rank_boost)
      select	okres_kod,
      		okres_nazev,
      		obec_kod,
      		obec_nazev,
      		cast_obce_kod,
      		cast_obce_nazev,
      		ulice_kod,
      		ulice_nazev,
      		nextval('ruian.rn_fulltext_adresy_id_seq'),
      		fulltext,
      		rank_boost
      		from
      (
      select  distinct
      		ok.KOD OKRES_KOD,
      		ok.NAZEV OKRES_NAZEV,
      		ob.kod OBEC_KOD,
      		ob.nazev OBEC_NAZEV,
      		cob.KOD CAST_OBCE_KOD,
      		cob.NAZEV CAST_OBCE_NAZEV,
      		ul.KOD ULICE_KOD,
      		ul.nazev ULICE_NAZEV,
      coalesce(ok.NAZEV,'')  || ' ' ||
      		ob.nazev || ' ' ||
      		cob.NAZEV || ' ' ||
      		coalesce(ul.nazev, ' ')
       as fulltext,
      10 rank_boost
      from ruian.rn_obec_b ob
      join ruian.rn_cast_obce_b cob on ob.kod = cob.obec_kod
      join ruian.rn_stavebni_objekt_b stav on stav.cobce_kod = cob.kod
      join ruian.rn_adresni_misto_b adr on adr.stavobj_kod = stav.kod
      join ruian.rn_stavebni_objekt_b so on so.kod = adr.stavobj_kod
      left join ruian.RN_OKRES_B ok on ob.OKRES_KOD = ok.KOD
      left join ruian.RN_ULICE_L ul on adr.ulice_kod = ul.kod
      ) xx;

      -- Naplnění tabulky částmi obcí
      insert into ruian.rn_fulltext_adresy (okres_kod,
      		okres_nazev,
      		obec_kod,
      		obec_nazev,
      		cast_obce_kod,
      		cast_obce_nazev,
      		ID,
      		fulltext,
      		rank_boost)
      select	okres_kod,
      		okres_nazev,
      		obec_kod,
      		obec_nazev,
      		cast_obce_kod,
      		cast_obce_nazev,
      		nextval('ruian.rn_fulltext_adresy_id_seq'),
      		fulltext,
      		rank_boost
      		from
      (
      select  distinct
      		ok.KOD OKRES_KOD,
      		ok.NAZEV OKRES_NAZEV,
      		ob.kod OBEC_KOD,
      		ob.nazev OBEC_NAZEV,
      		cob.KOD CAST_OBCE_KOD,
      		cob.NAZEV CAST_OBCE_NAZEV,
      coalesce(ok.NAZEV,'')  || ' ' ||
      		ob.nazev || ' ' ||
      		cob.NAZEV
       as fulltext,
      40 rank_boost
      from ruian.rn_obec_b ob
      join ruian.rn_cast_obce_b cob on ob.kod = cob.obec_kod
      left join ruian.RN_OKRES_B ok on ob.OKRES_KOD = ok.KOD
      ) xx;

      -- Naplnění tabulky obcemi
      insert into ruian.rn_fulltext_adresy (okres_kod,
      		okres_nazev,
      		obec_kod,
      		obec_nazev,
      		ID,
      		fulltext,
      		rank_boost)
      select	okres_kod,
      		okres_nazev,
      		obec_kod,
      		obec_nazev,
      		nextval('ruian.rn_fulltext_adresy_id_seq'),
      		fulltext,
      		rank_boost
      		from
      (
      select  distinct
      		ok.KOD OKRES_KOD,
      		ok.NAZEV OKRES_NAZEV,
      		ob.kod OBEC_KOD,
      		ob.nazev OBEC_NAZEV,
      coalesce(ok.NAZEV,'')  || ' ' ||
      		ob.nazev
       as fulltext,
      100 rank_boost
      from ruian.rn_obec_b ob
      left join ruian.RN_OKRES_B ok on ob.OKRES_KOD = ok.KOD
      ) xx;

      --update fulltext vektoru
      UPDATE ruian.rn_fulltext_adresy SET tsv =
          setweight(to_tsvector(coalesce(okres_nazev,'')), 'A')    ||
          setweight(to_tsvector(coalesce(obec_nazev,'')), 'B')  ||
          setweight(to_tsvector(coalesce(cast_obce_nazev,'')), 'C') ||
          setweight(to_tsvector(coalesce(ulice_nazev,'')), 'D') ||
      	setweight(to_tsvector(coalesce(adresa_psc,'')), 'D') ||
      	setweight(to_tsvector(coalesce(cislo_cp,'')), 'D') ||
      	setweight(to_tsvector(coalesce(cislo_co,'')), 'D');

      select 1 as done;
    RESULT -> rn_verze (writer POSTGRES_1)

Bookmark: Truncate
Truncate_verze: SQLExecutor
    ATTR_IGNORE_NULLS = Yes
    COMBINE_ATTRS = Keep Initiator Attributes if Conflict
    COMBINE_GEOM = Initiator Geometry Only
    DATASET = $(DestDataset_MSSQL)
    FORMAT = MSSQL_SPATIAL
    MSSQL_SPATIAL_APPLICATION_INTENT = ReadWrite
    MSSQL_SPATIAL_COMMAND_TIMEOUT = 30
    MSSQL_SPATIAL_CREATE_FEATURE_TABLES_FROM_DATA = Yes
    MSSQL_SPATIAL_NAMED_CONNECTION = $(DestDataset_MSSQL)
    MSSQL_SPATIAL_QUERY_FEATURE_TYPES_FOR_MERGE_FILTERS = Yes
    OUTPUT_FEATURES_DISPLAY = Data Features
    SQL_STATEMENT:
      EXEC dbo.TRUNCATE_RN_TABLES;

      ALTER SEQUENCE TB_UFID_S RESTART WITH 1;
Truncate_verze_2: SQLExecutor
    ATTR_IGNORE_NULLS = Yes
    COMBINE_ATTRS = Keep Initiator Attributes if Conflict
    COMBINE_GEOM = Initiator Geometry Only
    DATASET = $(DestDataset_POSTGRES)
    FORMAT = POSTGRES
    OUTPUT_FEATURES_DISPLAY = Data Features
    POSTGRES_CREATE_FEATURE_TABLES_FROM_DATA = Yes
    POSTGRES_NAMED_CONNECTION = $(DestDataset_POSTGRES)
    POSTGRES_QUERY_FEATURE_TYPES_FOR_MERGE_FILTERS = Yes
    POSTGRES_READ_TIME_WITH_TIMEZONE = Yes
    POSTGRES_SCHEMAS_FOR_TABLE_LISTING = ruian
    SQL_STATEMENT:
      select ruian.truncate_rn_tables();

      SELECT  SETVAL(c.oid, 1)
      from pg_class c JOIN pg_namespace n
      on n.oid = c.relnamespace
      where c.relkind = 'S' and n.nspname = 'ruian' ;

      Insert into ruian.RN_VERZE (poradove_cislo, CISLO_VERZE, DATUM_AKTUALIZACE) VALUES (0,'1.0.7 FME', now());

Bookmark: Drop/disable indices
Disable_indices: SQLExecutor
    ATTR_IGNORE_NULLS = Yes
    COMBINE_ATTRS = Keep Initiator Attributes if Conflict
    COMBINE_GEOM = Initiator Geometry Only
    DATASET = $(DestDataset_MSSQL)
    FORMAT = MSSQL_SPATIAL
    MSSQL_SPATIAL_APPLICATION_INTENT = ReadWrite
    MSSQL_SPATIAL_COMMAND_TIMEOUT = 30
    MSSQL_SPATIAL_CREATE_FEATURE_TABLES_FROM_DATA = Yes
    MSSQL_SPATIAL_NAMED_CONNECTION = $(DestDataset_MSSQL)
    MSSQL_SPATIAL_QUERY_FEATURE_TYPES_FOR_MERGE_FILTERS = Yes
    OUTPUT_FEATURES_DISPLAY = Data Features
    SQL_STATEMENT:
      DECLARE @NAME VARCHAR(100)
      DECLARE @SQL NVARCHAR(500)
      DECLARE @disableT NVARCHAR(500)


      DECLARE CUR CURSOR FOR
        SELECT NAME
        FROM   SYS.TABLES
        WHERE  TYPE = 'U'
               AND SCHEMA_ID = 1
      	 and name like 'rn%'

      OPEN CUR

      FETCH NEXT FROM CUR INTO @NAME

      WHILE @@FETCH_STATUS = 0
       BEGIN
      	DECLARE @sql1 AS VARCHAR(MAX)='';

      	SELECT @sql1 = @sql1 +
      	'ALTER INDEX ' + sys.indexes.name + ' ON  ' + sys.objects.name + ' DISABLE;' +CHAR(13)+CHAR(10)
      	FROM
      		sys.indexes
      	JOIN
      		sys.objects
      		ON sys.indexes.object_id = sys.objects.object_id
      	WHERE sys.indexes.type_desc = 'NONCLUSTERED'
      	AND sys.objects.type_desc = @NAME;
      PRINT @sql1
      EXEC(@sql1);

       set @disableT = 'DISABLE TRIGGER ALL ON RUIAN.DBO.'+@NAME+';'
        PRINT @disableT
            EXEC Sp_executesql
              @disableT

           FETCH NEXT FROM CUR INTO @NAME
        END

      CLOSE CUR

      DEALLOCATE CUR
Drop_indices: SQLExecutor
    ATTR_IGNORE_NULLS = Yes
    COMBINE_ATTRS = Keep Initiator Attributes if Conflict
    COMBINE_GEOM = Initiator Geometry Only
    DATASET = $(DestDataset_POSTGRES)
    FORMAT = POSTGRES
    OUTPUT_FEATURES_DISPLAY = Data Features
    POSTGRES_CREATE_FEATURE_TABLES_FROM_DATA = Yes
    POSTGRES_NAMED_CONNECTION = $(DestDataset_POSTGRES)
    POSTGRES_QUERY_FEATURE_TYPES_FOR_MERGE_FILTERS = Yes
    POSTGRES_READ_TIME_WITH_TIMEZONE = Yes
    POSTGRES_SCHEMAS_FOR_TABLE_LISTING = ruian
    SQL_STATEMENT:
      FME_SQL_DELIMITER ;

      DROP INDEX IF EXISTS ruian.sidx_rn_adresni_misto_b_geom;
      DROP INDEX IF EXISTS ruian.rn_adresni_misto_b_ix1;
      DROP INDEX IF EXISTS ruian.rn_adresni_misto_b_ix2;
      DROP INDEX IF EXISTS ruian.rn_bonit_dily_parcel_ix2;
      DROP INDEX IF EXISTS ruian.rn_bonit_dily_parcel_ix1;
      DROP INDEX IF EXISTS ruian.sidx_rn_cast_obce_b_geom;
      DROP INDEX IF EXISTS ruian.rn_cast_obce_b_ix2;
      DROP INDEX IF EXISTS ruian.rn_detailni_tea_ix3;
      DROP INDEX IF EXISTS ruian.rn_detailni_tea_ix4;
      DROP INDEX IF EXISTS ruian.rn_detailni_tea_ix5;
      DROP INDEX IF EXISTS ruian.rn_detailni_tea_ix6;
      DROP INDEX IF EXISTS ruian.rn_detailni_tea_ix7;
      DROP INDEX IF EXISTS ruian.rn_detailni_tea_ix2;
      DROP INDEX IF EXISTS ruian.idx_fulltext_table;
      DROP INDEX IF EXISTS ruian.sidx_rn_katastralni_uzemi_b_geom;
      DROP INDEX IF EXISTS ruian.rn_katastralni_uzemi_b_ix2;
      DROP INDEX IF EXISTS ruian.sidx_rn_katastralni_uzemi_p_geom;
      DROP INDEX IF EXISTS ruian.rn_katastralni_uzemi_p_ix2;
      DROP INDEX IF EXISTS ruian.sidx_rn_kraj_1960_b_geom;
      DROP INDEX IF EXISTS ruian.rn_kraj_1960_b_ix2;
      DROP INDEX IF EXISTS ruian.sidx_rn_kraj_1960_p_geom;
      DROP INDEX IF EXISTS ruian.rn_kraj_1960_p_ix2;
      DROP INDEX IF EXISTS ruian.sidx_rn_momc_b_geom;
      DROP INDEX IF EXISTS ruian.rn_momc_b_ix2;
      DROP INDEX IF EXISTS ruian.rn_momc_b_ix3;
      DROP INDEX IF EXISTS ruian.rn_momc_b_ix4;
      DROP INDEX IF EXISTS ruian.sidx_rn_momc_p_geom;
      DROP INDEX IF EXISTS ruian.rn_momc_p_ix2;
      DROP INDEX IF EXISTS ruian.rn_momc_p_ix3;
      DROP INDEX IF EXISTS ruian.rn_momc_p_ix4;
      DROP INDEX IF EXISTS ruian.rn_momc_p_ix5;
      DROP INDEX IF EXISTS ruian.sidx_rn_mop_b_geom;
      DROP INDEX IF EXISTS ruian.rn_mop_b_ix2;
      DROP INDEX IF EXISTS ruian.sidx_rn_mop_p_geom;
      DROP INDEX IF EXISTS ruian.rn_mop_p_ix2;
      DROP INDEX IF EXISTS ruian.sidx_rn_obec_b_geom;
      DROP INDEX IF EXISTS ruian.rn_obec_b_ix2;
      DROP INDEX IF EXISTS ruian.rn_obec_b_ix3;
      DROP INDEX IF EXISTS ruian.rn_obec_b_ix4;
      DROP INDEX IF EXISTS ruian.rn_obec_b_ix5;
      DROP INDEX IF EXISTS ruian.rn_obec_b_ix6;
      DROP INDEX IF EXISTS ruian.sidx_rn_obec_p_geom;
      DROP INDEX IF EXISTS ruian.rn_obec_p_ix3;
      DROP INDEX IF EXISTS ruian.rn_obec_p_ix4;
      DROP INDEX IF EXISTS ruian.rn_obec_p_ix5;
      DROP INDEX IF EXISTS ruian.rn_obec_p_ix6;
      DROP INDEX IF EXISTS ruian.rn_obec_p_ix2;
      DROP INDEX IF EXISTS ruian.sidx_rn_okres_b_geom;
      DROP INDEX IF EXISTS ruian.rn_okres_b_ix2;
      DROP INDEX IF EXISTS ruian.rn_okres_b_ix3;
      DROP INDEX IF EXISTS ruian.sidx_rn_okres_p_geom;
      DROP INDEX IF EXISTS ruian.rn_okres_p_ix2;
      DROP INDEX IF EXISTS ruian.rn_okres_p_ix3;
      DROP INDEX IF EXISTS ruian.sidx_rn_orp_b_geom;
      DROP INDEX IF EXISTS ruian.rn_orp_b_ix2;
      DROP INDEX IF EXISTS ruian.rn_orp_b_ix3;
      DROP INDEX IF EXISTS ruian.sidx_rn_orp_p_geom;
      DROP INDEX IF EXISTS ruian.rn_orp_p_ix2;
      DROP INDEX IF EXISTS ruian.rn_orp_p_ix3;
      DROP INDEX IF EXISTS ruian.sidx_rn_parcela_b_geom;
      DROP INDEX IF EXISTS ruian.rn_parcela_b_ix2;
      DROP INDEX IF EXISTS ruian.rn_parcela_b_ix3;
      DROP INDEX IF EXISTS ruian.rn_parcela_b_ix4;
      DROP INDEX IF EXISTS ruian.rn_parcela_b_ix5;
      DROP INDEX IF EXISTS ruian.sidx_rn_parcela_p_geom;
      DROP INDEX IF EXISTS ruian.rn_parcela_p_ix2;
      DROP INDEX IF EXISTS ruian.rn_parcela_p_ix3;
      DROP INDEX IF EXISTS ruian.rn_parcela_p_ix4;
      DROP INDEX IF EXISTS ruian.rn_parcela_p_ix5;
      DROP INDEX IF EXISTS ruian.sidx_rn_pou_b_geom;
      DROP INDEX IF EXISTS ruian.rn_pou_b_ix2;
      DROP INDEX IF EXISTS ruian.rn_pou_b_ix3;
      DROP INDEX IF EXISTS ruian.sidx_rn_pou_p_geom;
      DROP INDEX IF EXISTS ruian.rn_pou_p_ix2;
      DROP INDEX IF EXISTS ruian.rn_pou_p_ix3;
      DROP INDEX IF EXISTS ruian.sidx_rn_region_soudrznosti_b_geom;
      DROP INDEX IF EXISTS ruian.rn_region_soudrznosti_b_ix2;
      DROP INDEX IF EXISTS ruian.sidx_rn_region_soudrznosti_p_geom;
      DROP INDEX IF EXISTS ruian.rn_region_soudrznosti_p_ix2;
      DROP INDEX IF EXISTS ruian.sidx_rn_spravni_obvod_b_geom;
      DROP INDEX IF EXISTS ruian.rn_spravni_obvod_b_ix2;
      DROP INDEX IF EXISTS ruian.rn_spravni_obvod_b_ix3;
      DROP INDEX IF EXISTS ruian.sidx_rn_spravni_obvod_p_geom;
      DROP INDEX IF EXISTS ruian.rn_spravni_obvod_p_ix2;
      DROP INDEX IF EXISTS ruian.rn_spravni_obvod_p_ix3;
      DROP INDEX IF EXISTS ruian.sidx_rn_stat_b_geom;
      DROP INDEX IF EXISTS ruian.sidx_rn_stat_p_geom;
      DROP INDEX IF EXISTS ruian.sidx_rn_stavebni_objekt_b_geom;
      DROP INDEX IF EXISTS ruian.rn_stavebni_objekt_b_ix5;
      DROP INDEX IF EXISTS ruian.rn_stavebni_objekt_b_ix6;
      DROP INDEX IF EXISTS ruian.rn_stavebni_objekt_b_ix7;
      DROP INDEX IF EXISTS ruian.rn_stavebni_objekt_b_ix8;
      DROP INDEX IF EXISTS ruian.rn_stavebni_objekt_b_ix9;
      DROP INDEX IF EXISTS ruian.rn_stavebni_objekt_b_ix10;
      DROP INDEX IF EXISTS ruian.rn_stavebni_objekt_b_ix11;
      DROP INDEX IF EXISTS ruian.rn_stavebni_objekt_b_ix12;
      DROP INDEX IF EXISTS ruian.rn_stavebni_objekt_b_ix2;
      DROP INDEX IF EXISTS ruian.rn_stavebni_objekt_b_ix3;
      DROP INDEX IF EXISTS ruian.rn_stavebni_objekt_b_ix4;
      DROP INDEX IF EXISTS ruian.sidx_rn_stavebni_objekt_p_geom;
      DROP INDEX IF EXISTS ruian.rn_stavebni_objekt_p_ix4;
      DROP INDEX IF EXISTS ruian.rn_stavebni_objekt_p_ix5;
      DROP INDEX IF EXISTS ruian.rn_stavebni_objekt_p_ix6;
      DROP INDEX IF EXISTS ruian.rn_stavebni_objekt_p_ix7;
      DROP INDEX IF EXISTS ruian.rn_stavebni_objekt_p_ix8;
      DROP INDEX IF EXISTS ruian.rn_stavebni_objekt_p_ix9;
      DROP INDEX IF EXISTS ruian.rn_stavebni_objekt_p_ix10;
      DROP INDEX IF EXISTS ruian.rn_stavebni_objekt_p_ix11;
      DROP INDEX IF EXISTS ruian.rn_stavebni_objekt_p_ix12;
      DROP INDEX IF EXISTS ruian.rn_stavebni_objekt_p_ix2;
      DROP INDEX IF EXISTS ruian.rn_stavebni_objekt_p_ix3;
      DROP INDEX IF EXISTS ruian.sidx_rn_ulice_l_geom;
      DROP INDEX IF EXISTS ruian.rn_ulice_l_ix2;
      DROP INDEX IF EXISTS ruian.sidx_rn_vusc_b_geom;
      DROP INDEX IF EXISTS ruian.rn_vusc_b_ix2;
      DROP INDEX IF EXISTS ruian.sidx_rn_vusc_p_geom;
      DROP INDEX IF EXISTS ruian.rn_vusc_p_ix2;
      DROP INDEX IF EXISTS ruian.rn_zpusob_ochrany_objektu_ix2;
      DROP INDEX IF EXISTS ruian.rn_zpusob_ochrany_objektu_p;
      DROP INDEX IF EXISTS ruian.rn_zpusob_ochrany_objektu_ix1;
      DROP INDEX IF EXISTS ruian.rn_zpusob_ochrany_pozemku_ix1;
      DROP INDEX IF EXISTS ruian.rn_zpusob_ochrany_pozemku_ix2;
      DROP INDEX IF EXISTS ruian.sidx_rn_zsj_b_geom;
      DROP INDEX IF EXISTS ruian.rn_zsj_b_ix2;
      DROP INDEX IF EXISTS ruian.rn_zsj_b_ix3;
      DROP INDEX IF EXISTS ruian.sidx_rn_zsj_p_geom;
      DROP INDEX IF EXISTS ruian.rn_zsj_p_ix2;
      DROP INDEX IF EXISTS ruian.rn_zsj_p_ix3;
      DROP INDEX IF EXISTS RN_ORP_B_OKRES_KOD_IX;
      DROP INDEX IF EXISTS RN_ORP_P_OKRES_KOD_IX;

Bookmark: DATUM AKTUALIZACE
AttributeManager
    ATTR_TABLE:
      SET_TO DATUM_AKTUALIZACE = @DateTimeNow()
      SET_TO ZPRACOVANY_SOUBOR = výběr obcí/státu - úplná kopie
      SET_TO DATUM_IMPORTU = $(VFR_DATE)
      SET_TO VERZE_VFR = 3.1
      SET_TO TYP_SOUBORU = UKSH
      SET_TO CISLO_VERZE = 1.0.7 FME
      SET_TO PREDCHOZI_SOUBOR = FME_NULL_VALUE
    -> TestFilter_21
TestFilter_21
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> Recreate_indices [INITIATOR]
    PostgreSQL -> Recreate_indices_2 [INITIATOR]
Recreate_indices: SQLExecutor
    ATTR_IGNORE_NULLS = Yes
    COMBINE_ATTRS = Keep Initiator Attributes if Conflict
    COMBINE_GEOM = Initiator Geometry Only
    DATASET = $(DestDataset_MSSQL)
    FORMAT = MSSQL_SPATIAL
    MSSQL_SPATIAL_APPLICATION_INTENT = ReadWrite
    MSSQL_SPATIAL_COMMAND_TIMEOUT = 30
    MSSQL_SPATIAL_CREATE_FEATURE_TABLES_FROM_DATA = Yes
    MSSQL_SPATIAL_NAMED_CONNECTION = $(DestDataset_MSSQL)
    MSSQL_SPATIAL_QUERY_FEATURE_TYPES_FOR_MERGE_FILTERS = Yes
    OUTPUT_FEATURES_DISPLAY = Data Features
    SQL_STATEMENT:
      DECLARE @NAME VARCHAR(100)
      DECLARE @rebuild_sql NVARCHAR(500)


      DECLARE CUR CURSOR FOR
        SELECT NAME
        FROM   SYS.TABLES
        WHERE  TYPE = 'U'
               AND SCHEMA_ID = 1
      	 and name like 'rn%'

      OPEN CUR

      FETCH NEXT FROM CUR INTO @NAME

      WHILE @@FETCH_STATUS = 0
      BEGIN
      	   set @rebuild_sql = 'ALTER INDEX ALL ON RUIAN.DBO.'+@NAME+' REBUILD;
      	   ENABLE TRIGGER ALL ON RUIAN.DBO.'+@NAME+';'
        PRINT @rebuild_sql
            EXEC Sp_executesql
              @rebuild_sql

            FETCH NEXT FROM CUR INTO @NAME
        END

      CLOSE CUR

      DEALLOCATE CUR ;

      select 1 as done;
    INITIATOR -> RN_VERZE (writer MSSQL_SPATIAL_2)
RN_VERZE (writer MSSQL_SPATIAL_2)
    attributes: CISLO_VERZE varchar(20), DATUM_AKTUALIZACE date, ZPRACOVANY_SOUBOR varchar(200), VERZE_VFR varchar(10), DATUM_IMPORTU date, TYP_SOUBORU varchar(10), PREDCHOZI_SOUBOR varchar(150)
Recreate_indices_2: SQLExecutor
    ATTR_IGNORE_NULLS = Yes
    COMBINE_ATTRS = Keep Initiator Attributes if Conflict
    COMBINE_GEOM = Initiator Geometry Only
    DATASET = $(DestDataset_POSTGRES)
    FORMAT = POSTGRES
    OUTPUT_FEATURES_DISPLAY = Data Features
    POSTGRES_CREATE_FEATURE_TABLES_FROM_DATA = Yes
    POSTGRES_NAMED_CONNECTION = $(DestDataset_POSTGRES)
    POSTGRES_QUERY_FEATURE_TYPES_FOR_MERGE_FILTERS = Yes
    POSTGRES_READ_TIME_WITH_TIMEZONE = Yes
    POSTGRES_SCHEMAS_FOR_TABLE_LISTING = ruian
    SQL_STATEMENT:
      FME_SQL_DELIMITER ;

      CREATE UNIQUE INDEX IF NOT EXISTS pk_rn_bonit_dily_parcel ON ruian.rn_bonit_dily_parcel USING btree (fid);
      CREATE UNIQUE INDEX IF NOT EXISTS un_rn_bonit_dily_parcel ON ruian.rn_bonit_dily_parcel USING btree (parcela_id, bpej_kod);
      CREATE INDEX IF NOT EXISTS rn_bonit_dily_parcel_ix2 ON ruian.rn_bonit_dily_parcel USING btree (parcela_id);
      CREATE INDEX IF NOT EXISTS rn_bonit_dily_parcel_ix1 ON ruian.rn_bonit_dily_parcel USING btree (bpej_kod);
      CREATE UNIQUE INDEX IF NOT EXISTS pk_rn_cast_obce_b ON ruian.rn_cast_obce_b USING btree (fid);
      CREATE UNIQUE INDEX IF NOT EXISTS un_rn_cast_obce_b ON ruian.rn_cast_obce_b USING btree (kod);
      CREATE INDEX IF NOT EXISTS sidx_rn_cast_obce_b_geom ON ruian.rn_cast_obce_b USING gist (geom);
      CREATE INDEX IF NOT EXISTS rn_cast_obce_b_ix2 ON ruian.rn_cast_obce_b USING btree (obec_kod);
      CREATE UNIQUE INDEX IF NOT EXISTS pk_rn_detailni_tea ON ruian.rn_detailni_tea USING btree (fid);
      CREATE UNIQUE INDEX IF NOT EXISTS un_rn_detailni_tea ON ruian.rn_detailni_tea USING btree (kod, stavobj_kod);
      CREATE INDEX IF NOT EXISTS rn_detailni_tea_ix3 ON ruian.rn_detailni_tea USING btree (stavobj_kod);
      CREATE INDEX IF NOT EXISTS rn_detailni_tea_ix4 ON ruian.rn_detailni_tea USING btree (druh_konstrukce_kod);
      CREATE INDEX IF NOT EXISTS rn_detailni_tea_ix5 ON ruian.rn_detailni_tea USING btree (pripoj_plyn_kod);
      CREATE INDEX IF NOT EXISTS rn_detailni_tea_ix6 ON ruian.rn_detailni_tea USING btree (pripoj_kanal_sit_kod);
      CREATE INDEX IF NOT EXISTS rn_detailni_tea_ix7 ON ruian.rn_detailni_tea USING btree (zpusob_vytapeni_kod);
      CREATE INDEX IF NOT EXISTS rn_detailni_tea_ix2 ON ruian.rn_detailni_tea USING btree (pripoj_vodovod_kod);
      CREATE UNIQUE INDEX IF NOT EXISTS pk_rn_katastralni_uzemi_b ON ruian.rn_katastralni_uzemi_b USING btree (fid);
      CREATE UNIQUE INDEX IF NOT EXISTS un_rn_katastralni_uzemi_b ON ruian.rn_katastralni_uzemi_b USING btree (kod);
      CREATE INDEX IF NOT EXISTS sidx_rn_katastralni_uzemi_b_geom ON ruian.rn_katastralni_uzemi_b USING gist (geom);
      CREATE INDEX IF NOT EXISTS rn_katastralni_uzemi_b_ix2 ON ruian.rn_katastralni_uzemi_b USING btree (obec_kod);
      CREATE UNIQUE INDEX IF NOT EXISTS pk_rn_vusc_b ON ruian.rn_vusc_b USING btree (fid);
      CREATE UNIQUE INDEX IF NOT EXISTS un_rn_vusc_b ON ruian.rn_vusc_b USING btree (kod);
      CREATE INDEX IF NOT EXISTS sidx_rn_vusc_b_geom ON ruian.rn_vusc_b USING gist (geom);
      CREATE INDEX IF NOT EXISTS rn_vusc_b_ix2 ON ruian.rn_vusc_b USING btree (regsoudr_kod);
      CREATE UNIQUE INDEX IF NOT EXISTS pk_rn_adresni_misto_b ON ruian.rn_adresni_misto_b USING btree (fid);
      CREATE UNIQUE INDEX IF NOT EXISTS un_rn_adresni_misto_b ON ruian.rn_adresni_misto_b USING btree (kod);
      CREATE INDEX IF NOT EXISTS sidx_rn_adresni_misto_b_geom ON ruian.rn_adresni_misto_b USING gist (geom);
      CREATE INDEX IF NOT EXISTS rn_adresni_misto_b_ix1 ON ruian.rn_adresni_misto_b USING btree (ulice_kod);
      CREATE INDEX IF NOT EXISTS rn_adresni_misto_b_ix2 ON ruian.rn_adresni_misto_b USING btree (stavobj_kod);
      CREATE UNIQUE INDEX IF NOT EXISTS pk_rn_zsj_p ON ruian.rn_zsj_p USING btree (fid);
      CREATE UNIQUE INDEX IF NOT EXISTS un_rn_zsj_p ON ruian.rn_zsj_p USING btree (kod);
      CREATE INDEX IF NOT EXISTS sidx_rn_zsj_p_geom ON ruian.rn_zsj_p USING gist (geom);
      CREATE INDEX IF NOT EXISTS rn_zsj_p_ix2 ON ruian.rn_zsj_p USING btree (charakter_zsj_kod);
      CREATE INDEX IF NOT EXISTS rn_zsj_p_ix3 ON ruian.rn_zsj_p USING btree (katuz_kod);
      CREATE UNIQUE INDEX IF NOT EXISTS pk_rn_katastralni_uzemi_p ON ruian.rn_katastralni_uzemi_p USING btree (fid);
      CREATE UNIQUE INDEX IF NOT EXISTS un_rn_katastralni_uzemi_p ON ruian.rn_katastralni_uzemi_p USING btree (kod);
      CREATE INDEX IF NOT EXISTS sidx_rn_katastralni_uzemi_p_geom ON ruian.rn_katastralni_uzemi_p USING gist (geom);
      CREATE INDEX IF NOT EXISTS rn_katastralni_uzemi_p_ix2 ON ruian.rn_katastralni_uzemi_p USING btree (obec_kod);
      CREATE UNIQUE INDEX IF NOT EXISTS pk_rn_kraj_1960_b ON ruian.rn_kraj_1960_b USING btree (fid);
      CREATE INDEX IF NOT EXISTS sidx_rn_kraj_1960_b_geom ON ruian.rn_kraj_1960_b USING gist (geom);
      CREATE INDEX IF NOT EXISTS rn_kraj_1960_b_ix2 ON ruian.rn_kraj_1960_b USING btree (stat_kod);
      CREATE UNIQUE INDEX IF NOT EXISTS pk_rn_kraj_1960_p ON ruian.rn_kraj_1960_p USING btree (fid);
      CREATE INDEX IF NOT EXISTS sidx_rn_kraj_1960_p_geom ON ruian.rn_kraj_1960_p USING gist (geom);
      CREATE INDEX IF NOT EXISTS rn_kraj_1960_p_ix2 ON ruian.rn_kraj_1960_p USING btree (stat_kod);
      CREATE UNIQUE INDEX IF NOT EXISTS pk_rn_momc_b ON ruian.rn_momc_b USING btree (fid);
      CREATE UNIQUE INDEX IF NOT EXISTS un_rn_momc_b ON ruian.rn_momc_b USING btree (kod);
      CREATE INDEX IF NOT EXISTS sidx_rn_momc_b_geom ON ruian.rn_momc_b USING gist (geom);
      CREATE INDEX IF NOT EXISTS rn_momc_b_ix2 ON ruian.rn_momc_b USING btree (obec_kod);
      CREATE INDEX IF NOT EXISTS rn_momc_b_ix3 ON ruian.rn_momc_b USING btree (pou_kod);
      CREATE INDEX IF NOT EXISTS rn_momc_b_ix4 ON ruian.rn_momc_b USING btree (spravobv_kod);
      CREATE UNIQUE INDEX IF NOT EXISTS pk_rn_momc_p ON ruian.rn_momc_p USING btree (fid);
      CREATE UNIQUE INDEX IF NOT EXISTS un_rn_momc_p ON ruian.rn_momc_p USING btree (kod);
      CREATE INDEX IF NOT EXISTS sidx_rn_momc_p_geom ON ruian.rn_momc_p USING gist (geom);
      CREATE INDEX IF NOT EXISTS rn_momc_p_ix2 ON ruian.rn_momc_p USING btree (spravobv_kod);
      CREATE INDEX IF NOT EXISTS rn_momc_p_ix3 ON ruian.rn_momc_p USING btree (pou_kod);
      CREATE INDEX IF NOT EXISTS rn_momc_p_ix4 ON ruian.rn_momc_p USING btree (mop_kod);
      CREATE INDEX IF NOT EXISTS rn_momc_p_ix5 ON ruian.rn_momc_p USING btree (obec_kod);
      CREATE UNIQUE INDEX IF NOT EXISTS pk_rn_mop_b ON ruian.rn_mop_b USING btree (fid);
      CREATE UNIQUE INDEX IF NOT EXISTS un_rn_mop_b ON ruian.rn_mop_b USING btree (kod);
      CREATE INDEX IF NOT EXISTS sidx_rn_mop_b_geom ON ruian.rn_mop_b USING gist (geom);
      CREATE INDEX IF NOT EXISTS rn_mop_b_ix2 ON ruian.rn_mop_b USING btree (obec_kod);
      CREATE UNIQUE INDEX IF NOT EXISTS pk_rn_mop_p ON ruian.rn_mop_p USING btree (fid);
      CREATE UNIQUE INDEX IF NOT EXISTS un_rn_mop_p ON ruian.rn_mop_p USING btree (kod);
      CREATE INDEX IF NOT EXISTS sidx_rn_mop_p_geom ON ruian.rn_mop_p USING gist (geom);
      CREATE INDEX IF NOT EXISTS rn_mop_p_ix2 ON ruian.rn_mop_p USING btree (obec_kod);
      CREATE UNIQUE INDEX IF NOT EXISTS pk_rn_obec_b ON ruian.rn_obec_b USING btree (fid);
      CREATE UNIQUE INDEX IF NOT EXISTS un_rn_obec_b ON ruian.rn_obec_b USING btree (kod);
      CREATE INDEX IF NOT EXISTS sidx_rn_obec_b_geom ON ruian.rn_obec_b USING gist (geom);
      CREATE INDEX IF NOT EXISTS rn_obec_b_ix2 ON ruian.rn_obec_b USING btree (pou_kod);
      CREATE INDEX IF NOT EXISTS rn_obec_b_ix3 ON ruian.rn_obec_b USING btree (okres_kod);
      CREATE INDEX IF NOT EXISTS rn_obec_b_ix4 ON ruian.rn_obec_b USING btree (cleneni_sm_rozsah_kod);
      CREATE INDEX IF NOT EXISTS rn_obec_b_ix5 ON ruian.rn_obec_b USING btree (cleneni_sm_typ_kod);
      CREATE INDEX IF NOT EXISTS rn_obec_b_ix6 ON ruian.rn_obec_b USING btree (status_kod);
      CREATE UNIQUE INDEX IF NOT EXISTS pk_rn_obec_p ON ruian.rn_obec_p USING btree (fid);
      CREATE UNIQUE INDEX IF NOT EXISTS un_rn_obec_p ON ruian.rn_obec_p USING btree (kod);
      CREATE INDEX IF NOT EXISTS sidx_rn_obec_p_geom ON ruian.rn_obec_p USING gist (geom);
      CREATE INDEX IF NOT EXISTS rn_obec_p_ix3 ON ruian.rn_obec_p USING btree (okres_kod);
      CREATE INDEX IF NOT EXISTS rn_obec_p_ix4 ON ruian.rn_obec_p USING btree (cleneni_sm_rozsah_kod);
      CREATE INDEX IF NOT EXISTS rn_obec_p_ix5 ON ruian.rn_obec_p USING btree (cleneni_sm_typ_kod);
      CREATE INDEX IF NOT EXISTS rn_obec_p_ix6 ON ruian.rn_obec_p USING btree (status_kod);
      CREATE INDEX IF NOT EXISTS rn_obec_p_ix2 ON ruian.rn_obec_p USING btree (pou_kod);
      CREATE UNIQUE INDEX IF NOT EXISTS pk_rn_okres_b ON ruian.rn_okres_b USING btree (fid);
      CREATE UNIQUE INDEX IF NOT EXISTS un_rn_okres_b ON ruian.rn_okres_b USING btree (kod);
      CREATE INDEX IF NOT EXISTS sidx_rn_okres_b_geom ON ruian.rn_okres_b USING gist (geom);
      CREATE INDEX IF NOT EXISTS rn_okres_b_ix2 ON ruian.rn_okres_b USING btree (vusc_kod);
      CREATE INDEX IF NOT EXISTS rn_okres_b_ix3 ON ruian.rn_okres_b USING btree (kraj_1960_kod);
      CREATE UNIQUE INDEX IF NOT EXISTS pk_rn_okres_p ON ruian.rn_okres_p USING btree (fid);
      CREATE UNIQUE INDEX IF NOT EXISTS un_rn_okres_p ON ruian.rn_okres_p USING btree (kod);
      CREATE INDEX IF NOT EXISTS sidx_rn_okres_p_geom ON ruian.rn_okres_p USING gist (geom);
      CREATE INDEX IF NOT EXISTS rn_okres_p_ix2 ON ruian.rn_okres_p USING btree (kraj_1960_kod);
      CREATE INDEX IF NOT EXISTS rn_okres_p_ix3 ON ruian.rn_okres_p USING btree (vusc_kod);
      CREATE UNIQUE INDEX IF NOT EXISTS pk_rn_orp_b ON ruian.rn_orp_b USING btree (fid);
      CREATE UNIQUE INDEX IF NOT EXISTS un_rn_orp_b ON ruian.rn_orp_b USING btree (kod);
      CREATE INDEX IF NOT EXISTS sidx_rn_orp_b_geom ON ruian.rn_orp_b USING gist (geom);
      CREATE INDEX IF NOT EXISTS rn_orp_b_ix2 ON ruian.rn_orp_b USING btree (vusc_kod);
      CREATE INDEX IF NOT EXISTS rn_orp_b_ix3 ON ruian.rn_orp_b USING btree (spravni_obec_kod);
      CREATE UNIQUE INDEX IF NOT EXISTS pk_rn_zpusob_ochrany_pozemku ON ruian.rn_zpusob_ochrany_pozemku USING btree (fid);
      CREATE UNIQUE INDEX IF NOT EXISTS un_rn_zpusob_ochrany_pozemku ON ruian.rn_zpusob_ochrany_pozemku USING btree (parcela_id, zpusob_ochrany_kod);
      CREATE INDEX IF NOT EXISTS rn_zpusob_ochrany_pozemku_ix1 ON ruian.rn_zpusob_ochrany_pozemku USING btree (parcela_id);
      CREATE INDEX IF NOT EXISTS rn_zpusob_ochrany_pozemku_ix2 ON ruian.rn_zpusob_ochrany_pozemku USING btree (zpusob_ochrany_kod);
      CREATE UNIQUE INDEX IF NOT EXISTS pk_rn_zsj_b ON ruian.rn_zsj_b USING btree (fid);
      CREATE UNIQUE INDEX IF NOT EXISTS un_rn_zsj_b ON ruian.rn_zsj_b USING btree (kod);
      CREATE INDEX IF NOT EXISTS sidx_rn_zsj_b_geom ON ruian.rn_zsj_b USING gist (geom);
      CREATE INDEX IF NOT EXISTS rn_zsj_b_ix2 ON ruian.rn_zsj_b USING btree (charakter_zsj_kod);
      CREATE INDEX IF NOT EXISTS rn_zsj_b_ix3 ON ruian.rn_zsj_b USING btree (katuz_kod);
      CREATE UNIQUE INDEX IF NOT EXISTS pk_rn_orp_p ON ruian.rn_orp_p USING btree (fid);
      CREATE UNIQUE INDEX IF NOT EXISTS un_rn_orp_p ON ruian.rn_orp_p USING btree (kod);
      CREATE INDEX IF NOT EXISTS sidx_rn_orp_p_geom ON ruian.rn_orp_p USING gist (geom);
      CREATE INDEX IF NOT EXISTS rn_orp_p_ix2 ON ruian.rn_orp_p USING btree (vusc_kod);
      CREATE INDEX IF NOT EXISTS rn_orp_p_ix3 ON ruian.rn_orp_p USING btree (spravni_obec_kod);
      CREATE UNIQUE INDEX IF NOT EXISTS pk_rn_parcela_b ON ruian.rn_parcela_b USING btree (fid);
      CREATE UNIQUE INDEX IF NOT EXISTS un_rn_parcela_b ON ruian.rn_parcela_b USING btree (id);
      CREATE INDEX IF NOT EXISTS sidx_rn_parcela_b_geom ON ruian.rn_parcela_b USING gist (geom);
      CREATE INDEX IF NOT EXISTS rn_parcela_b_ix2 ON ruian.rn_parcela_b USING btree (druh_pozemku_kod);
      CREATE INDEX IF NOT EXISTS rn_parcela_b_ix3 ON ruian.rn_parcela_b USING btree (zpusob_vyu_poz_kod);
      CREATE INDEX IF NOT EXISTS rn_parcela_b_ix4 ON ruian.rn_parcela_b USING btree (druh_cislovani_kod);
      CREATE INDEX IF NOT EXISTS rn_parcela_b_ix5 ON ruian.rn_parcela_b USING btree (katuz_kod);
      CREATE UNIQUE INDEX IF NOT EXISTS pk_rn_parcela_p ON ruian.rn_parcela_p USING btree (fid);
      CREATE UNIQUE INDEX IF NOT EXISTS un_rn_parcela_p ON ruian.rn_parcela_p USING btree (id);
      CREATE INDEX IF NOT EXISTS sidx_rn_parcela_p_geom ON ruian.rn_parcela_p USING gist (geom);
      CREATE INDEX IF NOT EXISTS rn_parcela_p_ix2 ON ruian.rn_parcela_p USING btree (druh_pozemku_kod);
      CREATE INDEX IF NOT EXISTS rn_parcela_p_ix3 ON ruian.rn_parcela_p USING btree (zpusob_vyu_poz_kod);
      CREATE INDEX IF NOT EXISTS rn_parcela_p_ix4 ON ruian.rn_parcela_p USING btree (druh_cislovani_kod);
      CREATE INDEX IF NOT EXISTS rn_parcela_p_ix5 ON ruian.rn_parcela_p USING btree (katuz_kod);
      CREATE UNIQUE INDEX IF NOT EXISTS pk_rn_pou_b ON ruian.rn_pou_b USING btree (fid);
      CREATE UNIQUE INDEX IF NOT EXISTS un_rn_pou_b ON ruian.rn_pou_b USING btree (kod);
      CREATE INDEX IF NOT EXISTS sidx_rn_pou_b_geom ON ruian.rn_pou_b USING gist (geom);
      CREATE INDEX IF NOT EXISTS rn_pou_b_ix2 ON ruian.rn_pou_b USING btree (orp_kod);
      CREATE INDEX IF NOT EXISTS rn_pou_b_ix3 ON ruian.rn_pou_b USING btree (spravni_obec_kod);
      CREATE UNIQUE INDEX IF NOT EXISTS pk_rn_pou_p ON ruian.rn_pou_p USING btree (fid);
      CREATE UNIQUE INDEX IF NOT EXISTS un_rn_pou_p ON ruian.rn_pou_p USING btree (kod);
      CREATE INDEX IF NOT EXISTS sidx_rn_pou_p_geom ON ruian.rn_pou_p USING gist (geom);
      CREATE INDEX IF NOT EXISTS rn_pou_p_ix2 ON ruian.rn_pou_p USING btree (orp_kod);
      CREATE INDEX IF NOT EXISTS rn_pou_p_ix3 ON ruian.rn_pou_p USING btree (spravni_obec_kod);
      CREATE UNIQUE INDEX IF NOT EXISTS pk_rn_region_soudrznosti_b ON ruian.rn_region_soudrznosti_b USING btree (fid);
      CREATE UNIQUE INDEX IF NOT EXISTS un_rn_region_soudrznosti_b ON ruian.rn_region_soudrznosti_b USING btree (kod);
      CREATE INDEX IF NOT EXISTS sidx_rn_region_soudrznosti_b_geom ON ruian.rn_region_soudrznosti_b USING gist (geom);
      CREATE INDEX IF NOT EXISTS rn_region_soudrznosti_b_ix2 ON ruian.rn_region_soudrznosti_b USING btree (stat_kod);
      CREATE UNIQUE INDEX IF NOT EXISTS pk_rn_region_soudrznosti_p ON ruian.rn_region_soudrznosti_p USING btree (fid);
      CREATE UNIQUE INDEX IF NOT EXISTS un_rn_region_soudrznosti_p ON ruian.rn_region_soudrznosti_p USING btree (kod);
      CREATE INDEX IF NOT EXISTS sidx_rn_region_soudrznosti_p_geom ON ruian.rn_region_soudrznosti_p USING gist (geom);
      CREATE INDEX IF NOT EXISTS rn_region_soudrznosti_p_ix2 ON ruian.rn_region_soudrznosti_p USING btree (stat_kod);
      CREATE UNIQUE INDEX IF NOT EXISTS pk_rn_spravni_obvod_b ON ruian.rn_spravni_obvod_b USING btree (fid);
      CREATE UNIQUE INDEX IF NOT EXISTS un_rn_spravni_obvod_b ON ruian.rn_spravni_obvod_b USING btree (kod);
      CREATE INDEX IF NOT EXISTS sidx_rn_spravni_obvod_b_geom ON ruian.rn_spravni_obvod_b USING gist (geom);
      CREATE INDEX IF NOT EXISTS rn_spravni_obvod_b_ix2 ON ruian.rn_spravni_obvod_b USING btree (spravni_momc_kod);
      CREATE INDEX IF NOT EXISTS rn_spravni_obvod_b_ix3 ON ruian.rn_spravni_obvod_b USING btree (obec_kod);
      CREATE UNIQUE INDEX IF NOT EXISTS pk_rn_spravni_obvod_p ON ruian.rn_spravni_obvod_p USING btree (fid);
      CREATE UNIQUE INDEX IF NOT EXISTS un_rn_spravni_obvod_p ON ruian.rn_spravni_obvod_p USING btree (kod);
      CREATE INDEX IF NOT EXISTS sidx_rn_spravni_obvod_p_geom ON ruian.rn_spravni_obvod_p USING gist (geom);
      CREATE INDEX IF NOT EXISTS rn_spravni_obvod_p_ix2 ON ruian.rn_spravni_obvod_p USING btree (obec_kod);
      CREATE INDEX IF NOT EXISTS rn_spravni_obvod_p_ix3 ON ruian.rn_spravni_obvod_p USING btree (spravni_momc_kod);
      CREATE UNIQUE INDEX IF NOT EXISTS pk_rn_stat_b ON ruian.rn_stat_b USING btree (fid);
      CREATE UNIQUE INDEX IF NOT EXISTS un_rn_stat_b ON ruian.rn_stat_b USING btree (kod);
      CREATE INDEX IF NOT EXISTS sidx_rn_stat_b_geom ON ruian.rn_stat_b USING gist (geom);
      CREATE UNIQUE INDEX IF NOT EXISTS pk_rn_stat_p ON ruian.rn_stat_p USING btree (fid);
      CREATE UNIQUE INDEX IF NOT EXISTS un_rn_stat_p ON ruian.rn_stat_p USING btree (kod);
      CREATE INDEX IF NOT EXISTS sidx_rn_stat_p_geom ON ruian.rn_stat_p USING gist (geom);
      CREATE UNIQUE INDEX IF NOT EXISTS pk_rn_stavebni_objekt_b ON ruian.rn_stavebni_objekt_b USING btree (fid);
      CREATE UNIQUE INDEX IF NOT EXISTS un_rn_stavebni_objekt_b ON ruian.rn_stavebni_objekt_b USING btree (kod);
      CREATE INDEX IF NOT EXISTS sidx_rn_stavebni_objekt_b_geom ON ruian.rn_stavebni_objekt_b USING gist (geom);
      CREATE INDEX IF NOT EXISTS rn_stavebni_objekt_b_ix5 ON ruian.rn_stavebni_objekt_b USING btree (je_vytah_kod);
      CREATE INDEX IF NOT EXISTS rn_stavebni_objekt_b_ix6 ON ruian.rn_stavebni_objekt_b USING btree (identifikacni_parcela_id);
      CREATE INDEX IF NOT EXISTS rn_stavebni_objekt_b_ix7 ON ruian.rn_stavebni_objekt_b USING btree (momc_kod);
      CREATE INDEX IF NOT EXISTS rn_stavebni_objekt_b_ix8 ON ruian.rn_stavebni_objekt_b USING btree (typ_kod);
      CREATE INDEX IF NOT EXISTS rn_stavebni_objekt_b_ix9 ON ruian.rn_stavebni_objekt_b USING btree (zpusob_vyuziti_kod);
      CREATE INDEX IF NOT EXISTS rn_stavebni_objekt_b_ix10 ON ruian.rn_stavebni_objekt_b USING btree (druh_konstrukce_kod);
      CREATE INDEX IF NOT EXISTS rn_stavebni_objekt_b_ix11 ON ruian.rn_stavebni_objekt_b USING btree (pripoj_plyn_kod);
      CREATE INDEX IF NOT EXISTS rn_stavebni_objekt_b_ix12 ON ruian.rn_stavebni_objekt_b USING btree (zpusob_vytapeni_kod);
      CREATE INDEX IF NOT EXISTS rn_stavebni_objekt_b_ix2 ON ruian.rn_stavebni_objekt_b USING btree (pripoj_kanal_sit_kod);
      CREATE INDEX IF NOT EXISTS rn_stavebni_objekt_b_ix3 ON ruian.rn_stavebni_objekt_b USING btree (pripoj_vodovod_kod);
      CREATE INDEX IF NOT EXISTS rn_stavebni_objekt_b_ix4 ON ruian.rn_stavebni_objekt_b USING btree (cobce_kod);
      CREATE UNIQUE INDEX IF NOT EXISTS pk_rn_stavebni_objekt_p ON ruian.rn_stavebni_objekt_p USING btree (fid);
      CREATE UNIQUE INDEX IF NOT EXISTS un_rn_stavebni_objekt_p ON ruian.rn_stavebni_objekt_p USING btree (kod);
      CREATE INDEX IF NOT EXISTS sidx_rn_stavebni_objekt_p_geom ON ruian.rn_stavebni_objekt_p USING gist (geom);
      CREATE INDEX IF NOT EXISTS rn_stavebni_objekt_p_ix4 ON ruian.rn_stavebni_objekt_p USING btree (je_vytah_kod);
      CREATE INDEX IF NOT EXISTS rn_stavebni_objekt_p_ix5 ON ruian.rn_stavebni_objekt_p USING btree (identifikacni_parcela_id);
      CREATE INDEX IF NOT EXISTS rn_stavebni_objekt_p_ix6 ON ruian.rn_stavebni_objekt_p USING btree (momc_kod);
      CREATE INDEX IF NOT EXISTS rn_stavebni_objekt_p_ix7 ON ruian.rn_stavebni_objekt_p USING btree (typ_kod);
      CREATE INDEX IF NOT EXISTS rn_stavebni_objekt_p_ix8 ON ruian.rn_stavebni_objekt_p USING btree (druh_konstrukce_kod);
      CREATE INDEX IF NOT EXISTS rn_stavebni_objekt_p_ix9 ON ruian.rn_stavebni_objekt_p USING btree (zpusob_vyuziti_kod);
      CREATE INDEX IF NOT EXISTS rn_stavebni_objekt_p_ix10 ON ruian.rn_stavebni_objekt_p USING btree (pripoj_plyn_kod);
      CREATE INDEX IF NOT EXISTS rn_stavebni_objekt_p_ix11 ON ruian.rn_stavebni_objekt_p USING btree (zpusob_vytapeni_kod);
      CREATE INDEX IF NOT EXISTS rn_stavebni_objekt_p_ix12 ON ruian.rn_stavebni_objekt_p USING btree (pripoj_kanal_sit_kod);
      CREATE INDEX IF NOT EXISTS rn_stavebni_objekt_p_ix2 ON ruian.rn_stavebni_objekt_p USING btree (pripoj_vodovod_kod);
      CREATE INDEX IF NOT EXISTS rn_stavebni_objekt_p_ix3 ON ruian.rn_stavebni_objekt_p USING btree (cobce_kod);
      CREATE UNIQUE INDEX IF NOT EXISTS pk_rn_ulice_l ON ruian.rn_ulice_l USING btree (fid);
      CREATE UNIQUE INDEX IF NOT EXISTS un_rn_ulice_l ON ruian.rn_ulice_l USING btree (kod);
      CREATE INDEX IF NOT EXISTS sidx_rn_ulice_l_geom ON ruian.rn_ulice_l USING gist (geom);
      CREATE INDEX IF NOT EXISTS rn_ulice_l_ix2 ON ruian.rn_ulice_l USING btree (obec_kod);
      CREATE UNIQUE INDEX IF NOT EXISTS pk_rn_vusc_p ON ruian.rn_vusc_p USING btree (fid);
      CREATE UNIQUE INDEX IF NOT EXISTS un_rn_vusc_p ON ruian.rn_vusc_p USING btree (kod);
      CREATE INDEX IF NOT EXISTS sidx_rn_vusc_p_geom ON ruian.rn_vusc_p USING gist (geom);
      CREATE INDEX IF NOT EXISTS rn_vusc_p_ix2 ON ruian.rn_vusc_p USING btree (regsoudr_kod);
      CREATE UNIQUE INDEX IF NOT EXISTS pk_rn_zpusob_ochrany_objektu ON ruian.rn_zpusob_ochrany_objektu USING btree (fid);
      CREATE UNIQUE INDEX IF NOT EXISTS un_rn_zpusob_ochrany_objektu ON ruian.rn_zpusob_ochrany_objektu USING btree (stavobj_kod, zpusob_ochrany_kod);
      CREATE INDEX IF NOT EXISTS rn_zpusob_ochrany_objektu_ix2 ON ruian.rn_zpusob_ochrany_objektu USING btree (zpusob_ochrany_kod);
      CREATE UNIQUE INDEX IF NOT EXISTS rn_zpusob_ochrany_objektu_p ON ruian.rn_zpusob_ochrany_objektu USING btree (fid);
      CREATE INDEX IF NOT EXISTS rn_zpusob_ochrany_objektu_ix1 ON ruian.rn_zpusob_ochrany_objektu USING btree (stavobj_kod);

       	select 1 as done;
    RESULT -> Ruian_Service_Fulltext
rn_verze (writer POSTGRES_1)
    attributes: cislo_verze text, datum_aktualizace date, verze_vfr text, zpracovany_soubor text, datum_importu date, typ_souboru text, predchozi_soubor text
