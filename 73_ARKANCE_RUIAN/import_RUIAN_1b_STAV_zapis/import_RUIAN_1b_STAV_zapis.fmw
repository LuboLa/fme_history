FME workspace import_RUIAN_1b_STAV_zapis.fmw

Parameters:
- FILE_URL = D:\temp\20230731_OB_560812_UKSH.xml.zip   # "" File url
- DB_TYPE = PostgreSQL   # DB type
- DestDataset_MSSQL = MSSQL RUIAN   # SQL Server Connection MSSQL
- DestDataset_POSTGIS = PG_FME_RUIAN   # Connection PGSQL

Writers:
- MSSQL_SPATIAL_2: MSSQL_SPATIAL to $(DestDataset_MSSQL)
- POSTGIS_1: POSTGIS to $(DestDataset_POSTGIS)
- POSTGRES_1: POSTGRES to $(DestDataset_POSTGIS)

Note: Vytvoření dummy
Creator_2
    GEOMTYPE = Geometry Object
    NUM = 1
    CREATED -> AttributeCreator_23
AttributeCreator_23
    ATTR_TABLE = SET_TO _response_file_path = $(FILE_URL)
    -> FeatureReader [INITIATOR]
    -> FeatureReader_2 [INITIATOR]
Note: ÚROVEŇ STÁT
Note: ÚROVEŇ OBEC
Note: Načtení dat VFR
FeatureReader
    ATTRIBUTES =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
    ATTR_ACCUM_MODE = Only Use Result
    COMBINE_GEOM = Use Result
    CUZK_GML_ADD_GEOMETRIES_AS_XML_FRAGMENTS = NO
    CUZK_GML_DISABLE_XML_NAMESPACE_PROCESSING = NO
    CUZK_GML_ENFORCE_PATH_CONTINUITY_BY = SNAPPING_END_POINTS
    CUZK_GML_EXPLORE_XSD_VALUES = NO
    CUZK_GML_FEATURE_TYPES_SCHEMA_MODE = XML_SCHEMA
    CUZK_GML_FLATTEN_XML_FRAGMENTS = NO
    CUZK_GML_MAP_COMPLEX_PROPERTIES_AS = Nested Attributes
    CUZK_GML_MAP_EMBEDDED_OBJECTS_AS = ATTRIBUTES
    CUZK_GML_MAP_GEOMETRY_COLUMNS = YES
    CUZK_GML_MAP_PREDEFINED_GML_PROPERTIES = YES
    CUZK_GML_SKIP_SCHEMA_LOCATION_IN_DATASET = No
    CUZK_GML_SUPPORTED_READER_ARCHIVE_EXTENSIONS = xml.gz,gml.gz
    CUZK_GML_USE_OLD_READER = NO
    CUZK_GML_USE_SEARCH_ENVELOPE = NO
    CUZK_GML_VALIDATE_DATASET = no
    CUZK_GML_XML_FRAGMENTS_AS_DOCUMENTS = YES
    DATASET = @Value(_response_file_path)
    FORMAT = CUZK_GML
    INTERACT = NONE
    OUTPUT_FEATURES_DISPLAY = Schema and Data Features
    SELECTED_PORTS = AdresniMisto CastObce Hlavicka KatastralniUzemi Kraj Momc Mop Obec Okres Orp Parcela Pou RegionSoudrznosti SpravniObvod Stat StavebniObjekt Ulice Vusc Zsj
    AdresniMisto -> AttributeKeeper
    CastObce -> AttributeKeeper_2
    KatastralniUzemi -> AttributeKeeper_3
    Momc -> AttributeKeeper_15
    Mop -> AttributeKeeper_16
    Obec -> AttributeKeeper_4
    Okres -> AttributeKeeper_9
    Orp -> AttributeKeeper_10
    Parcela -> AttributeKeeper_5
    Parcela -> Tester_3
    Parcela -> Tester_6
    Pou -> AttributeKeeper_11
    RegionSoudrznosti -> AttributeKeeper_12
    SpravniObvod -> AttributeKeeper_17
    Stat -> AttributeKeeper_13
    StavebniObjekt -> AttributeKeeper_6
    StavebniObjekt -> Tester_4
    Ulice -> AttributeKeeper_7
    Vusc -> AttributeKeeper_14
    Zsj -> AttributeKeeper_8
TestFilter
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_ADRESNI_MISTO_B (writer MSSQL_SPATIAL_2)
    PostgreSQL -> rn_adresni_misto_b (writer POSTGIS_1)
TestFilter_2
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_ADRESNI_MISTO_B (writer MSSQL_SPATIAL_2)
    PostgreSQL -> rn_adresni_misto_b (writer POSTGIS_1)
TestFilter_3
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_CAST_OBCE_B (writer MSSQL_SPATIAL_2)
    PostgreSQL -> rn_cast_obce_b (writer POSTGIS_1)
TestFilter_4
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_KATASTRALNI_UZEMI_B (writer MSSQL_SPATIAL_2)
    PostgreSQL -> rn_katastralni_uzemi_b (writer POSTGIS_1)
TestFilter_5
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_KATASTRALNI_UZEMI_P (writer MSSQL_SPATIAL_2)
    PostgreSQL -> rn_katastralni_uzemi_p (writer POSTGIS_1)
TestFilter_6
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_MOMC_B (writer MSSQL_SPATIAL_2)
    PostgreSQL -> rn_momc_b (writer POSTGIS_1)
TestFilter_7
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_MOMC_P (writer MSSQL_SPATIAL_2)
    PostgreSQL -> rn_momc_p (writer POSTGIS_1)
TestFilter_8
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_MOP_B (writer MSSQL_SPATIAL_2)
    PostgreSQL -> rn_mop_b (writer POSTGIS_1)
TestFilter_9
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_MOP_P (writer MSSQL_SPATIAL_2)
    PostgreSQL -> rn_mop_p (writer POSTGIS_1)
TestFilter_10
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_OBEC_B (writer MSSQL_SPATIAL_2)
    PostgreSQL -> rn_obec_b (writer POSTGIS_1)
TestFilter_11
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_OBEC_P (writer MSSQL_SPATIAL_2)
    PostgreSQL -> rn_obec_p (writer POSTGIS_1)
TestFilter_12
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_OKRES_B (writer MSSQL_SPATIAL_2)
    PostgreSQL -> rn_okres_b (writer POSTGIS_1)
TestFilter_13
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_OKRES_P (writer MSSQL_SPATIAL_2)
    PostgreSQL -> rn_okres_p (writer POSTGIS_1)
TestFilter_14
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_ORP_B (writer MSSQL_SPATIAL_2)
    PostgreSQL -> rn_orp_b (writer POSTGIS_1)
TestFilter_15
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_ORP_P (writer MSSQL_SPATIAL_2)
    PostgreSQL -> rn_orp_p (writer POSTGIS_1)
TestFilter_16
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_PARCELA_B (writer MSSQL_SPATIAL_2)
    PostgreSQL -> rn_parcela_b (writer POSTGIS_1)
TestFilter_17
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_PARCELA_P (writer MSSQL_SPATIAL_2)
    PostgreSQL -> rn_parcela_p (writer POSTGIS_1)
TestFilter_32
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_BONIT_DILY_PARCEL (writer MSSQL_SPATIAL_2)
    PostgreSQL -> rn_bonit_dily_parcel (writer POSTGRES_1)
TestFilter_33
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_ZPUSOB_OCHRANY_POZEMKU (writer MSSQL_SPATIAL_2)
    PostgreSQL -> rn_zpusob_ochrany_pozemku (writer POSTGRES_1)
TestFilter_18
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_POU_B (writer MSSQL_SPATIAL_2)
    PostgreSQL -> rn_pou_b (writer POSTGIS_1)
TestFilter_19
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_POU_P (writer MSSQL_SPATIAL_2)
    PostgreSQL -> rn_pou_p (writer POSTGIS_1)
TestFilter_20
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_REGION_SOUDRZNOSTI_B (writer MSSQL_SPATIAL_2)
    PostgreSQL -> rn_region_soudrznosti_b (writer POSTGIS_1)
TestFilter_21
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_REGION_SOUDRZNOSTI_P (writer MSSQL_SPATIAL_2)
    PostgreSQL -> rn_region_soudrznosti_p (writer POSTGIS_1)
TestFilter_22
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_SPRAVNI_OBVOD_B (writer MSSQL_SPATIAL_2)
    PostgreSQL -> rn_spravni_obvod_b (writer POSTGIS_1)
TestFilter_23
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_SPRAVNI_OBVOD_P (writer MSSQL_SPATIAL_2)
    PostgreSQL -> rn_spravni_obvod_p (writer POSTGIS_1)
TestFilter_24
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_STAT_B (writer MSSQL_SPATIAL_2)
    PostgreSQL -> rn_stat_b (writer POSTGIS_1)
TestFilter_25
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_STAT_P (writer MSSQL_SPATIAL_2)
    PostgreSQL -> rn_stat_p (writer POSTGIS_1)
TestFilter_26
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_STAVEBNI_OBJEKT_B (writer MSSQL_SPATIAL_2)
    PostgreSQL -> rn_stavebni_objekt_b (writer POSTGIS_1)
TestFilter_27
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_STAVEBNI_OBJEKT_P (writer MSSQL_SPATIAL_2)
    PostgreSQL -> rn_stavebni_objekt_p (writer POSTGIS_1)
TestFilter_34
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_DETAILNI_TEA (writer MSSQL_SPATIAL_2)
    PostgreSQL -> rn_detailni_tea (writer POSTGRES_1)
TestFilter_36
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_ULICE_L (writer MSSQL_SPATIAL_2)
    PostgreSQL -> rn_ulice_l (writer POSTGIS_1)
TestFilter_28
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_VUSC_B (writer MSSQL_SPATIAL_2)
    PostgreSQL -> rn_vusc_b (writer POSTGIS_1)
TestFilter_29
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_VUSC_P (writer MSSQL_SPATIAL_2)
    PostgreSQL -> rn_vusc_p (writer POSTGIS_1)
TestFilter_30
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_ZSJ_B (writer MSSQL_SPATIAL_2)
    PostgreSQL -> rn_zsj_b (writer POSTGIS_1)
TestFilter_31
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_ZSJ_P (writer MSSQL_SPATIAL_2)
    PostgreSQL -> rn_zsj_p (writer POSTGIS_1)
FeatureReader_2
    ATTRIBUTES = StavebniObjekt,"CastObce.Kod,CislaDomovni.CisloDomovni,CislaDomovni.CisloDomovni{},DetailniTEA.DetailniTEA{}.AdresniMistoKod.Kod,DetailniTEA.DetailniTEA{}.DruhKonstrukceKod,DetailniTEA.DetailniTEA{}.GlobalniIdNavrhuZmeny,DetailniTEA.DetailniTEA{}.Kod,DetailniTEA.DetailniTEA{}.PlatiOd,DetailniTEA.DetailniTEA{}.PocetBytu,DetailniTEA.DetailniTEA{}.PocetPodlazi,DetailniTEA.DetailniTEA{}.PripojeniKanalizaceKod,DetailniTEA.DetailniTEA{}.PripojeniPlynKod,DetailniTEA.DetailniTEA{}.PripojeniVodovodKod,DetailniTEA.DetailniTEA{}.ZpusobVytapeniKod,Dokonceni,DruhKonstrukceKod,Geometrie.DefinicniBod.Point.id,Geometrie.DefinicniBod.Point.pos,Geometrie.DefinicniBod.Point.srsDimension,Geometrie.DefinicniBod.Point.srsName,Geometrie.OriginalniHranice.MultiSurface.id,Geometrie.OriginalniHranice.MultiSurface.srsDimension,Geometrie.OriginalniHranice.MultiSurface.srsName,Geometrie.OriginalniHranice.MultiSurface.surfaceMember.Polygon.exterior.LinearRing.posList,Geometrie.OriginalniHranice.MultiSurface.surfaceMember.Polygon.exterior.Ring.curveMember{}.Curve.id,Geometrie.OriginalniHranice.MultiSurface.surfaceMember.Polygon.exterior.Ring.curveMember{}.Curve.segments.ArcString.posList,Geometrie.OriginalniHranice.MultiSurface.surfaceMember.Polygon.exterior.Ring.curveMember{}.LineString.id,Geometrie.OriginalniHranice.MultiSurface.surfaceMember.Polygon.exterior.Ring.curveMember{}.LineString.posList,Geometrie.OriginalniHranice.MultiSurface.surfaceMember.Polygon.id,Geometrie.OriginalniHranice.MultiSurface.surfaceMember.Polygon.interior.LinearRing.posList,Geometrie.OriginalniHranice.MultiSurface.surfaceMember{}.Polygon.exterior.LinearRing.posList,Geometrie.OriginalniHranice.MultiSurface.surfaceMember{}.Polygon.id,GlobalniIdNavrhuZmeny,IdTransakce,IdentifikacniParcela.Id,IsknBudovaId,Kod,ObestavenyProstor,PlatiOd,PocetBytu,PocetPodlazi,PodlahovaPlocha,PripojeniKanalizaceKod,PripojeniPlynKod,PripojeniVodovodKod,StavebniObjekt.id,TypStavebnihoObjektuKod,VybaveniVytahemKod,ZastavenaPlocha,ZpusobVytapeniKod,ZpusobVyuzitiKod,ZpusobyOchrany.ZpusobOchrany.IdTransakce,ZpusobyOchrany.ZpusobOchrany.Kod,ZpusobyOchrany.ZpusobOchrany.RizeniId,ZpusobyOchrany.ZpusobOchrany.TypOchranyKod,ZpusobyOchrany.ZpusobOchrany{}.IdTransakce,ZpusobyOchrany.ZpusobOchrany{}.Kod,ZpusobyOchrany.ZpusobOchrany{}.RizeniId,ZpusobyOchrany.ZpusobOchrany{}.TypOchranyKod,xml_fragment,xml_id,xml_matched_element,xml_parent_child_pos,xml_parent_id"
    ATTR_ACCUM_MODE = Only Use Result
    COMBINE_GEOM = Use Result
    DATASET = @Value(_response_file_path)
    FORMAT = XML
    INTERACT = NONE
    OUTPUT_FEATURES_DISPLAY = Schema and Data Features
    XML_CONTINUE_ON_GEOM_ERROR = no
    XML_FILE_TYPE = Feature Paths
    XML_SUPPORTED_READER_ARCHIVE_EXTENSIONS = xml.gz,gml.gz
    XML_USE_SEARCH_ENVELOPE = NO
    XML_VALIDATE_DATASET = no
    XML_VALIDATE_XFMAP = no
    XML_XFMAP_FEATURE_PATHS = VymennyFormat/Data/StavebniObjekty/StavebniObjekt
    XML_XFMAP_FEATURE_PATHS_STRUCTURE:
      <structure
      separator="."
      map-empty-elements="yes"
      matched-prefix="attributes"
      matched-attributes="yes"
      cardinality="+{?}"
      except-expression=""
      structure-prefix=""
      child-position-attribute=""
      attribute-identifier=""
      ui-mode="basic"/>
    StavebniObjekt -> Tester_5
TestFilter_35
    DEFAULT_VALUE = <UNFILTERED>
    PASSED_TEST_GROUP_OUTPUT = FIRST
    TEST_LIST = "BOOL_OP,OR,COMPOSITE_TEST,""""""1"""""",TEST_CLAUSE,TEST $(DB_TYPE) = MSSQL",MSSQL,"BOOL_OP,OR,COMPOSITE_TEST,""""""1"""""",TEST_CLAUSE,TEST $(DB_TYPE) = PostgreSQL",PostgreSQL
    MSSQL -> RN_ZPUSOB_OCHRANY_OBJEKTU (writer MSSQL_SPATIAL_2)
    PostgreSQL -> rn_zpusob_ochrany_objektu (writer POSTGRES_1)

Bookmark: ADRESNI MISTO
AttributeKeeper
    CREATE_BULK_MODE_FEATURES = NO
    KEEP_ATTRS = CisloDomovni,CisloOrientacni,CisloOrientacniPismeno,GlobalniIdNavrhuZmeny,IdTransakce,Kod,Nespravny,PlatiDo,PlatiOd,Psc,VOKod,StavebniObjekt.Kod,Ulice.Kod
    -> DateTimeConverter
DateTimeConverter
    DATETIME_ATTR = PlatiDo PlatiOd
    IN_FORMAT = ISO
    OUT_FORMAT = FME
    PASSTHROUGH = YES
    REPAIR_INPUT = NO
    TEST_INPUT = 2013-12-05T00:00:00
    -> AttributeManager
AttributeManager
    ATTR_TABLE:
      SET_TO ZMENA_GRAFIKY = N
      SET_TO PUVOD = 1
      SET_TO PLATI_OD = @TimeZoneSet(@Value(PlatiOd),+01:00,auto)
      SET_TO ORIENTATION = 90
      SET_TO ID_TRANS_RUIAN = @Value(IdTransakce)
      SET_TO NZ_ID_GLOBALNI = @Value(GlobalniIdNavrhuZmeny)
      RENAME_SET_VALUE Kod > KOD
      RENAME_SET_VALUE Nespravny > NESPRAVNY = FME_CONDITIONAL:DEFAULT_VALUE'FME_NULL_VALUE'BOOL_OP;OR;COMPOSITE_TEST;1;TEST @Value(Nespravny) = true'1'FME_NUM_CONDITIONS2___
      RENAME_SET_VALUE CisloDomovni > CISLO_DOMOVNI
      RENAME_SET_VALUE CisloOrientacni > CISLO_ORIENTACNI_HODNOTA
      RENAME_SET_VALUE CisloOrientacniPismeno > CISLO_ORIENTACNI_PISMENO
      RENAME_SET_VALUE Psc > ADRP_PSC
      RENAME_SET_VALUE StavebniObjekt.Kod > STAVOBJ_KOD
      RENAME_SET_VALUE Ulice.Kod > ULICE_KOD
      REMOVE PlatiOd
      RENAME_SET_VALUE PlatiDo > PLATI_DO
      RENAME_SET_VALUE IdTransakce > ID_TRANS_RUIAN
      RENAME_SET_VALUE GlobalniIdNavrhuZmeny > NZ_ID_GLOBALNI
    -> GeometryRefiner_36
GeometryRefiner_36
    -> GeometryFilter_27
GeometryFilter_27
    FILTER_MODE = COMPLETE
    FILTER_MULTI = FILTER_TYPES]"MultiPoint Point"]INSTANCES]INSTANCE]FME_CONTROLLER_QUERY_FILE]]FME_CONTROLLER_CHOICE]Complete
    Point -> TestFilter_2
    MultiPoint -> GeometryPartExtractor
    <UNFILTERED> -> TestFilter_2
GeometryPartExtractor
    GQUERY:
      for $geom in //geometry
      where $geom/@fme_geometry_name = 'Geometrie.DefinicniBod.AdresniBod'
      return number($geom/@fme_id)
    EXTRACTED -> TestFilter

Bookmark: MSSQL - RUIAN schema ASC
RN_ADRESNI_MISTO_B (writer MSSQL_SPATIAL_2)
    attributes: ORIENTATION numeric(6,3), ADRP_PSC integer, CISLO_DOMOVNI smallint, CISLO_ORIENTACNI_HODNOTA smallint, CISLO_ORIENTACNI_PISMENO char(1), ID_TRANS_RUIAN bigint, KOD integer, NESPRAVNY varchar(1), NZ_ID_GLOBALNI bigint, PLATI_OD datetime2(0), STAVOBJ_KOD integer, ULICE_KOD integer, ZMENA_GRAFIKY varchar(1), PUVOD smallint
RN_CAST_OBCE_B (writer MSSQL_SPATIAL_2)
    attributes: ORIENTATION numeric(6,3), ID_TRANS_RUIAN bigint, KOD numeric(20,10), MLUV_CHAR_PAD_2 varchar(48), MLUV_CHAR_PAD_3 varchar(48), MLUV_CHAR_PAD_4 varchar(48), MLUV_CHAR_PAD_5 varchar(48), MLUV_CHAR_PAD_6 varchar(48), MLUV_CHAR_PAD_7 varchar(48), NAZEV varchar(48), NESPRAVNY varchar(1), NZ_ID_GLOBALNI bigint, OBEC_KOD integer, PLATI_OD datetime2(0), ZMENA_GRAFIKY varchar(1), PUVOD smallint
RN_KATASTRALNI_UZEMI_B (writer MSSQL_SPATIAL_2)
    attributes: ORIENTATION numeric(6,3), ID_TRANS_RUIAN bigint, KOD numeric(20,10), MA_DKM varchar(1), MLUV_CHAR_PAD_2 varchar(48), MLUV_CHAR_PAD_3 varchar(48), MLUV_CHAR_PAD_4 varchar(48), MLUV_CHAR_PAD_5 varchar(48), MLUV_CHAR_PAD_6 varchar(48), MLUV_CHAR_PAD_7 varchar(48), NAZEV varchar(48), NESPRAVNY varchar(1), NZ_ID_GLOBALNI bigint, OBEC_KOD integer, PLATI_OD datetime2(0), RIZENI_ID bigint, PUVOD smallint
RN_KATASTRALNI_UZEMI_P (writer MSSQL_SPATIAL_2)
    attributes: ID_TRANS_RUIAN bigint, KOD integer, MA_DKM varchar(1), MLUV_CHAR_PAD_2 varchar(48), MLUV_CHAR_PAD_3 varchar(48), MLUV_CHAR_PAD_4 varchar(48), MLUV_CHAR_PAD_5 varchar(48), MLUV_CHAR_PAD_6 varchar(48), MLUV_CHAR_PAD_7 varchar(48), NAZEV varchar(48), NESPRAVNY varchar(1), NZ_ID_GLOBALNI bigint, OBEC_KOD integer, PLATI_OD datetime2(0), RIZENI_ID bigint, PUVOD smallint
RN_MOMC_B (writer MSSQL_SPATIAL_2)
    attributes: ORIENTATION numeric(6,3), ID_TRANS_RUIAN bigint, KOD numeric(20,10), MLUV_CHAR_PAD_2 varchar(48), MLUV_CHAR_PAD_3 varchar(48), MLUV_CHAR_PAD_4 varchar(48), MLUV_CHAR_PAD_5 varchar(48), MLUV_CHAR_PAD_6 varchar(48), MLUV_CHAR_PAD_7 varchar(48), MOP_KOD smallint, NAZEV varchar(48), NESPRAVNY varchar(1), NZ_ID_GLOBALNI bigint, OBEC_KOD integer, PLATI_OD datetime2(0), POU_KOD smallint, SPRAVOBV_KOD smallint, VLAJKA_OBRAZEK varbinary_max, VLAJKA_TEXT varchar(4000), ZMENA_GRAFIKY varchar(1), ZNAK_OBRAZEK varbinary_max, ZNAK_TEXT varchar(4000), PUVOD smallint
RN_MOMC_P (writer MSSQL_SPATIAL_2)
    attributes: ID_TRANS_RUIAN bigint, KOD integer, MLUV_CHAR_PAD_2 varchar(48), MLUV_CHAR_PAD_3 varchar(48), MLUV_CHAR_PAD_4 varchar(48), MLUV_CHAR_PAD_5 varchar(48), MLUV_CHAR_PAD_6 varchar(48), MLUV_CHAR_PAD_7 varchar(48), MOP_KOD smallint, NAZEV varchar(48), NESPRAVNY varchar(1), NZ_ID_GLOBALNI bigint, OBEC_KOD integer, PLATI_OD datetime2(0), POU_KOD smallint, SPRAVOBV_KOD smallint, VLAJKA_OBRAZEK varbinary_max, VLAJKA_TEXT varchar(4000), ZMENA_GRAFIKY varchar(1), ZNAK_OBRAZEK varbinary_max, ZNAK_TEXT varchar(4000), PUVOD smallint
RN_MOP_B (writer MSSQL_SPATIAL_2)
    attributes: ORIENTATION numeric(6,3), ID_TRANS_RUIAN bigint, KOD numeric(20,10), NAZEV varchar(32), NESPRAVNY varchar(1), NZ_ID_GLOBALNI bigint, OBEC_KOD integer, PLATI_OD datetime2(0), ZMENA_GRAFIKY varchar(1), PUVOD smallint
RN_MOP_P (writer MSSQL_SPATIAL_2)
    attributes: ID_TRANS_RUIAN bigint, KOD smallint, NAZEV varchar(32), NESPRAVNY varchar(1), NZ_ID_GLOBALNI bigint, OBEC_KOD integer, PLATI_OD datetime2(0), ZMENA_GRAFIKY varchar(1), PUVOD smallint
RN_OBEC_B (writer MSSQL_SPATIAL_2)
    attributes: ORIENTATION numeric(6,3), CLENENI_SM_ROZSAH_KOD smallint, CLENENI_SM_TYP_KOD numeric(20,10), ID_TRANS_RUIAN bigint, KOD integer, MLUV_CHAR_PAD_2 varchar(48), MLUV_CHAR_PAD_3 varchar(48), MLUV_CHAR_PAD_4 varchar(48), MLUV_CHAR_PAD_5 varchar(48), MLUV_CHAR_PAD_6 varchar(48), MLUV_CHAR_PAD_7 varchar(48), NAZEV varchar(48), NESPRAVNY varchar(1), NZ_ID_GLOBALNI bigint, OKRES_KOD smallint, PLATI_OD datetime2(0), POU_KOD smallint, STATUS_KOD smallint, VLAJKA_OBRAZEK varbinary_max, VLAJKA_TEXT varchar(4000), ZMENA_GRAFIKY varchar(1), ZNAK_OBRAZEK varbinary_max, ZNAK_TEXT varchar(4000), PUVOD smallint
RN_OBEC_P (writer MSSQL_SPATIAL_2)
    attributes: CLENENI_SM_ROZSAH_KOD smallint, CLENENI_SM_TYP_KOD smallint, ID_TRANS_RUIAN bigint, KOD integer, MLUV_CHAR_PAD_2 varchar(48), MLUV_CHAR_PAD_3 varchar(48), MLUV_CHAR_PAD_4 varchar(48), MLUV_CHAR_PAD_5 varchar(48), MLUV_CHAR_PAD_6 varchar(48), MLUV_CHAR_PAD_7 varchar(48), NAZEV varchar(48), NESPRAVNY varchar(1), NZ_ID_GLOBALNI bigint, OKRES_KOD smallint, PLATI_OD datetime2(0), POU_KOD smallint, STATUS_KOD smallint, VLAJKA_OBRAZEK varbinary_max, VLAJKA_TEXT varchar(4000), ZMENA_GRAFIKY varchar(1), ZNAK_OBRAZEK varbinary_max, ZNAK_TEXT varchar(4000), PUVOD smallint
RN_OKRES_B (writer MSSQL_SPATIAL_2)
    attributes: ORIENTATION numeric(6,3), ID_TRANS_RUIAN bigint, KOD smallint, NAZEV varchar(32), NESPRAVNY varchar(1), NUTS_LAU varchar(6), NZ_ID_GLOBALNI bigint, PLATI_OD datetime2(0), VUSC_KOD smallint, ZMENA_GRAFIKY varchar(1), PUVOD smallint
RN_OKRES_P (writer MSSQL_SPATIAL_2)
    attributes: ID_TRANS_RUIAN bigint, KOD smallint, NAZEV varchar(32), NESPRAVNY varchar(1), NUTS_LAU varchar(6), NZ_ID_GLOBALNI bigint, PLATI_OD datetime2(0), VUSC_KOD smallint, ZMENA_GRAFIKY varchar(1), PUVOD smallint
RN_ORP_B (writer MSSQL_SPATIAL_2)
    attributes: ORIENTATION numeric(6,3), ID_TRANS_RUIAN bigint, KOD smallint, NAZEV varchar(48), NESPRAVNY varchar(1), NZ_ID_GLOBALNI bigint, PLATI_OD datetime2(0), SPRAVNI_OBEC_KOD integer, VUSC_KOD smallint, ZMENA_GRAFIKY varchar(1), PUVOD smallint
RN_ORP_P (writer MSSQL_SPATIAL_2)
    attributes: ID_TRANS_RUIAN bigint, KOD smallint, NAZEV varchar(48), NESPRAVNY varchar(1), NZ_ID_GLOBALNI bigint, PLATI_OD datetime2(0), SPRAVNI_OBEC_KOD integer, VUSC_KOD smallint, ZMENA_GRAFIKY varchar(1), PUVOD smallint
RN_PARCELA_B (writer MSSQL_SPATIAL_2)
    attributes: ORIENTATION numeric(6,3), DRUH_CISLOVANI_KOD smallint, DRUH_POZEMKU_KOD numeric(20,10), ID bigint, ID_TRANS_RUIAN bigint, KATUZ_KOD integer, KMENOVE_CISLO integer, NESPRAVNY varchar(1), PLATI_OD datetime2(0), PODDELENI_CISLA smallint, RIZENI_ID bigint, VYMERA_PARCELY bigint, ZPUSOB_VYU_POZ_KOD smallint, PUVOD smallint
RN_PARCELA_P (writer MSSQL_SPATIAL_2)
    attributes: DRUH_CISLOVANI_KOD smallint, DRUH_POZEMKU_KOD smallint, ID bigint, ID_TRANS_RUIAN bigint, KATUZ_KOD integer, KMENOVE_CISLO integer, NESPRAVNY varchar(1), PLATI_OD datetime2(0), PODDELENI_CISLA smallint, RIZENI_ID bigint, VYMERA_PARCELY bigint, ZPUSOB_VYU_POZ_KOD smallint, PUVOD smallint
RN_BONIT_DILY_PARCEL (writer MSSQL_SPATIAL_2)
    attributes: BPEJ_KOD integer, ID_TRANS_RUIAN bigint, PARCELA_ID bigint, RIZENI_ID bigint, VYMERA integer, PUVOD smallint
RN_ZPUSOB_OCHRANY_POZEMKU (writer MSSQL_SPATIAL_2)
    attributes: ID_TRANS_RUIAN bigint, PARCELA_ID bigint, RIZENI_ID bigint, ZPUSOB_OCHRANY_KOD smallint, PUVOD smallint
RN_POU_B (writer MSSQL_SPATIAL_2)
    attributes: ORIENTATION numeric(6,3), ID_TRANS_RUIAN bigint, KOD numeric(20,10), NAZEV varchar(48), NESPRAVNY varchar(1), NZ_ID_GLOBALNI bigint, ORP_KOD smallint, PLATI_OD datetime2(0), SPRAVNI_OBEC_KOD integer, ZMENA_GRAFIKY varchar(1), PUVOD smallint
RN_POU_P (writer MSSQL_SPATIAL_2)
    attributes: ID_TRANS_RUIAN bigint, KOD smallint, NAZEV varchar(48), NESPRAVNY varchar(1), NZ_ID_GLOBALNI bigint, ORP_KOD smallint, PLATI_OD datetime2(0), SPRAVNI_OBEC_KOD integer, ZMENA_GRAFIKY varchar(1), PUVOD smallint
RN_REGION_SOUDRZNOSTI_B (writer MSSQL_SPATIAL_2)
    attributes: ORIENTATION numeric(6,3), ID_TRANS_RUIAN bigint, KOD numeric(20,10), NAZEV varchar(32), NESPRAVNY varchar(1), NUTS_LAU varchar(6), NZ_ID_GLOBALNI bigint, PLATI_OD datetime2(0), STAT_KOD smallint, ZMENA_GRAFIKY varchar(1), PUVOD smallint
RN_REGION_SOUDRZNOSTI_P (writer MSSQL_SPATIAL_2)
    attributes: ID_TRANS_RUIAN bigint, KOD smallint, NAZEV varchar(32), NESPRAVNY varchar(1), NUTS_LAU varchar(6), NZ_ID_GLOBALNI bigint, PLATI_OD datetime2(0), STAT_KOD smallint, ZMENA_GRAFIKY varchar(1), PUVOD smallint
RN_SPRAVNI_OBVOD_B (writer MSSQL_SPATIAL_2)
    attributes: ORIENTATION numeric(6,3), ID_TRANS_RUIAN bigint, KOD numeric(20,10), NAZEV varchar(32), NESPRAVNY varchar(1), NZ_ID_GLOBALNI bigint, OBEC_KOD integer, PLATI_OD datetime2(0), SPRAVNI_MOMC_KOD integer, ZMENA_GRAFIKY varchar(1), PUVOD smallint
RN_SPRAVNI_OBVOD_P (writer MSSQL_SPATIAL_2)
    attributes: ID_TRANS_RUIAN bigint, KOD smallint, NAZEV varchar(32), NESPRAVNY varchar(1), NZ_ID_GLOBALNI bigint, OBEC_KOD integer, PLATI_OD datetime2(0), SPRAVNI_MOMC_KOD integer, ZMENA_GRAFIKY varchar(1), PUVOD smallint
RN_STAT_B (writer MSSQL_SPATIAL_2)
    attributes: ORIENTATION numeric(6,3), ID_TRANS_RUIAN bigint, KOD numeric(20,10), NAZEV varchar(32), NESPRAVNY varchar(1), NUTS_LAU varchar(6), NZ_ID_GLOBALNI bigint, PLATI_OD datetime2(0), ZMENA_GRAFIKY varchar(1), PUVOD smallint
RN_STAT_P (writer MSSQL_SPATIAL_2)
    attributes: ID_TRANS_RUIAN bigint, KOD smallint, NAZEV varchar(32), NESPRAVNY varchar(1), NUTS_LAU varchar(6), NZ_ID_GLOBALNI bigint, PLATI_OD datetime2(0), ZMENA_GRAFIKY varchar(1), PUVOD smallint
RN_STAVEBNI_OBJEKT_B (writer MSSQL_SPATIAL_2)
    attributes: ORIENTATION numeric(6,3), BUDOVA_ID bigint, COBCE_KOD numeric(20,10), DOKONCENI datetime2(0), DRUH_KONSTRUKCE_KOD smallint, ID_TRANS_RUIAN bigint, IDENTIFIKACNI_PARCELA_ID bigint, JE_VYTAH_KOD smallint, KOD integer, MOMC_KOD integer, NESPRAVNY varchar(1), NZ_ID_GLOBALNI bigint, OBESTAVENY_PROSTOR integer, PLATI_OD datetime2(0), POCET_BYTU smallint, POCET_PODLAZI smallint, PODLAHOVA_PLOCHA integer, PRIPOJ_KANAL_SIT_KOD smallint, PRIPOJ_PLYN_KOD smallint, PRIPOJ_VODOVOD_KOD smallint, TYP_KOD smallint, ZASTAVENA_PLOCHA integer, ZMENA_GRAFIKY varchar(1), ZPUSOB_VYTAPENI_KOD smallint, ZPUSOB_VYUZITI_KOD smallint, PUVOD smallint
RN_STAVEBNI_OBJEKT_P (writer MSSQL_SPATIAL_2)
    attributes: BUDOVA_ID bigint, COBCE_KOD integer, DOKONCENI datetime2(0), DRUH_KONSTRUKCE_KOD smallint, ID_TRANS_RUIAN bigint, IDENTIFIKACNI_PARCELA_ID bigint, JE_VYTAH_KOD smallint, KOD integer, MOMC_KOD integer, NESPRAVNY varchar(1), NZ_ID_GLOBALNI bigint, OBESTAVENY_PROSTOR integer, PLATI_OD datetime2(0), POCET_BYTU smallint, POCET_PODLAZI smallint, PODLAHOVA_PLOCHA integer, PRIPOJ_KANAL_SIT_KOD smallint, PRIPOJ_PLYN_KOD smallint, PRIPOJ_VODOVOD_KOD smallint, TYP_KOD smallint, ZASTAVENA_PLOCHA integer, ZMENA_GRAFIKY varchar(1), ZPUSOB_VYTAPENI_KOD smallint, ZPUSOB_VYUZITI_KOD smallint, PUVOD smallint
RN_DETAILNI_TEA (writer MSSQL_SPATIAL_2)
    attributes: DRUH_KONSTRUKCE_KOD smallint, KOD integer, NESPRAVNY varchar(1), NZ_ID_GLOBALNI bigint, PLATI_OD datetime2(0), POCET_BYTU smallint, POCET_PODLAZI smallint, PRIPOJ_KANAL_SIT_KOD smallint, PRIPOJ_PLYN_KOD smallint, PRIPOJ_VODOVOD_KOD smallint, STAVOBJ_KOD integer, ZPUSOB_VYTAPENI_KOD smallint, PUVOD smallint
RN_ULICE_L (writer MSSQL_SPATIAL_2)
    attributes: ID_TRANS_RUIAN bigint, KOD integer, NAZEV varchar(48), NESPRAVNY varchar(1), NZ_ID_GLOBALNI bigint, OBEC_KOD integer, PLATI_OD datetime2(0), ZMENA_GRAFIKY varchar(1), PUVOD smallint
RN_VUSC_B (writer MSSQL_SPATIAL_2)
    attributes: ORIENTATION numeric(6,3), ID_TRANS_RUIAN bigint, KOD numeric(20,10), NAZEV varchar(32), NESPRAVNY varchar(1), NUTS_LAU varchar(6), NZ_ID_GLOBALNI bigint, PLATI_OD datetime2(0), REGSOUDR_KOD smallint, ZMENA_GRAFIKY varchar(1), PUVOD smallint
RN_VUSC_P (writer MSSQL_SPATIAL_2)
    attributes: ID_TRANS_RUIAN bigint, KOD smallint, NAZEV varchar(32), NESPRAVNY varchar(1), NUTS_LAU varchar(6), NZ_ID_GLOBALNI bigint, PLATI_OD datetime2(0), REGSOUDR_KOD smallint, ZMENA_GRAFIKY varchar(1), PUVOD smallint
RN_ZSJ_B (writer MSSQL_SPATIAL_2)
    attributes: ORIENTATION numeric(6,3), CHARAKTER_ZSJ_KOD smallint, ID_TRANS_RUIAN numeric(20,10), KATUZ_KOD integer, KOD integer, MLUV_CHAR_PAD_2 varchar(48), MLUV_CHAR_PAD_3 varchar(48), MLUV_CHAR_PAD_4 varchar(48), MLUV_CHAR_PAD_5 varchar(48), MLUV_CHAR_PAD_6 varchar(48), MLUV_CHAR_PAD_7 varchar(48), NAZEV varchar(48), NESPRAVNY varchar(1), NZ_ID_GLOBALNI bigint, PLATI_OD datetime2(0), VYMERA bigint, ZMENA_GRAFIKY varchar(1), PUVOD smallint
RN_ZSJ_P (writer MSSQL_SPATIAL_2)
    attributes: CHARAKTER_ZSJ_KOD smallint, ID_TRANS_RUIAN bigint, KATUZ_KOD integer, KOD integer, MLUV_CHAR_PAD_2 varchar(48), MLUV_CHAR_PAD_3 varchar(48), MLUV_CHAR_PAD_4 varchar(48), MLUV_CHAR_PAD_5 varchar(48), MLUV_CHAR_PAD_6 varchar(48), MLUV_CHAR_PAD_7 varchar(48), NAZEV varchar(48), NESPRAVNY varchar(1), NZ_ID_GLOBALNI bigint, PLATI_OD datetime2(0), VYMERA bigint, ZMENA_GRAFIKY varchar(1), PUVOD smallint
RN_ZPUSOB_OCHRANY_OBJEKTU (writer MSSQL_SPATIAL_2)
    attributes: ID_TRANS_RUIAN bigint, RIZENI_ID bigint, STAVOBJ_KOD integer, ZPUSOB_OCHRANY_KOD smallint, PUVOD smallint

Bookmark: PGSQL - RUIAN schema ASC
rn_adresni_misto_b (writer POSTGIS_1)
    attributes: orientation numeric(6,3), adrp_psc int4, cislo_domovni int2, cislo_orientacni_hodnota int2, cislo_orientacni_pismeno char(1), id_trans_ruian int8, kod int4, nespravny varchar(1), nz_id_globalni int8, plati_od timestamptz, stavobj_kod int4, ulice_kod int4, zmena_grafiky varchar(1), puvod int2
rn_cast_obce_b (writer POSTGIS_1)
    attributes: orientation numeric(6,3), id_trans_ruian int8, kod numeric(20,10), mluv_char_pad_2 varchar(48), mluv_char_pad_3 varchar(48), mluv_char_pad_4 varchar(48), mluv_char_pad_5 varchar(48), mluv_char_pad_6 varchar(48), mluv_char_pad_7 varchar(48), nazev varchar(48), nespravny varchar(1), nz_id_globalni int8, obec_kod int4, plati_od timestamptz, zmena_grafiky varchar(1), puvod int2
rn_katastralni_uzemi_b (writer POSTGIS_1)
    attributes: orientation numeric(6,3), id_trans_ruian int8, kod int4, ma_dkm varchar(1), mluv_char_pad_2 varchar(48), mluv_char_pad_3 varchar(48), mluv_char_pad_4 varchar(48), mluv_char_pad_5 varchar(48), mluv_char_pad_6 varchar(48), mluv_char_pad_7 varchar(48), nazev varchar(48), nespravny varchar(1), nz_id_globalni int8, obec_kod int4, plati_od timestamptz, rizeni_id int8, puvod int2
rn_katastralni_uzemi_p (writer POSTGIS_1)
    attributes: id_trans_ruian int8, kod int8, ma_dkm varchar(1), mluv_char_pad_2 varchar(48), mluv_char_pad_3 varchar(48), mluv_char_pad_4 varchar(48), mluv_char_pad_5 varchar(48), mluv_char_pad_6 varchar(48), mluv_char_pad_7 varchar(48), nazev varchar(48), nespravny varchar(1), nz_id_globalni int8, obec_kod int4, plati_od timestamptz, rizeni_id int8, puvod int2
rn_momc_b (writer POSTGIS_1)
    attributes: orientation numeric(6,3), id_trans_ruian int8, kod int4, mluv_char_pad_2 numeric(48,10), mluv_char_pad_3 varchar(48), mluv_char_pad_4 varchar(48), mluv_char_pad_5 varchar(48), mluv_char_pad_6 varchar(48), mluv_char_pad_7 varchar(48), mop_kod int2, nazev varchar(48), nespravny varchar(1), nz_id_globalni int8, obec_kod int4, plati_od timestamptz, pou_kod int2, spravobv_kod int2, vlajka_obrazek bytea, vlajka_text varchar(4000), zmena_grafiky varchar(1), znak_obrazek bytea, znak_text varchar(4000), puvod int2
rn_momc_p (writer POSTGIS_1)
    attributes: id_trans_ruian int8, kod int8, mluv_char_pad_2 varchar(48), mluv_char_pad_3 varchar(48), mluv_char_pad_4 varchar(48), mluv_char_pad_5 varchar(48), mluv_char_pad_6 varchar(48), mluv_char_pad_7 varchar(48), mop_kod int2, nazev varchar(48), nespravny varchar(1), nz_id_globalni int8, obec_kod int4, plati_od timestamptz, pou_kod int2, spravobv_kod int2, vlajka_obrazek bytea, vlajka_text varchar(4000), zmena_grafiky varchar(1), znak_obrazek bytea, znak_text varchar(4000), puvod int2
rn_mop_b (writer POSTGIS_1)
    attributes: orientation numeric(6,3), id_trans_ruian int8, kod int2, nazev numeric(32,10), nespravny varchar(1), nz_id_globalni int8, obec_kod int4, plati_od timestamptz, zmena_grafiky varchar(1), puvod int2
rn_mop_p (writer POSTGIS_1)
    attributes: id_trans_ruian int8, kod int8, nazev varchar(32), nespravny varchar(1), nz_id_globalni int8, obec_kod int4, plati_od timestamptz, zmena_grafiky varchar(1), puvod int2
rn_obec_b (writer POSTGIS_1)
    attributes: orientation numeric(6,3), cleneni_sm_rozsah_kod int2, cleneni_sm_typ_kod int2, id_trans_ruian numeric(20,10), kod int4, mluv_char_pad_2 varchar(48), mluv_char_pad_3 varchar(48), mluv_char_pad_4 varchar(48), mluv_char_pad_5 varchar(48), mluv_char_pad_6 varchar(48), mluv_char_pad_7 varchar(48), nazev varchar(48), nespravny varchar(1), nz_id_globalni int8, okres_kod int2, plati_od timestamptz, pou_kod int2, status_kod int2, vlajka_obrazek bytea, vlajka_text varchar(4000), zmena_grafiky varchar(1), znak_obrazek bytea, znak_text varchar(4000), puvod int2
rn_obec_p (writer POSTGIS_1)
    attributes: cleneni_sm_rozsah_kod int2, cleneni_sm_typ_kod int2, id_trans_ruian int8, kod int4, mluv_char_pad_2 varchar(48), mluv_char_pad_3 varchar(48), mluv_char_pad_4 varchar(48), mluv_char_pad_5 varchar(48), mluv_char_pad_6 varchar(48), mluv_char_pad_7 varchar(48), nazev varchar(48), nespravny varchar(1), nz_id_globalni int8, okres_kod int2, plati_od timestamptz, pou_kod int2, status_kod int2, vlajka_obrazek bytea, vlajka_text varchar(4000), zmena_grafiky varchar(1), znak_obrazek bytea, znak_text varchar(4000), puvod int2
rn_okres_b (writer POSTGIS_1)
    attributes: orientation numeric(6,3), id_trans_ruian int8, kod int2, nazev varchar(32), nespravny varchar(1), nuts_lau varchar(6), nz_id_globalni int8, plati_od timestamptz, vusc_kod int2, zmena_grafiky varchar(1), puvod int2
rn_okres_p (writer POSTGIS_1)
    attributes: id_trans_ruian int8, kod int2, nazev varchar(32), nespravny varchar(1), nuts_lau varchar(6), nz_id_globalni int8, plati_od timestamptz, vusc_kod int2, zmena_grafiky varchar(1), puvod int2
rn_orp_b (writer POSTGIS_1)
    attributes: orientation numeric(6,3), id_trans_ruian int8, kod int2, nazev varchar(48), nespravny varchar(1), nz_id_globalni int8, plati_od timestamptz, spravni_obec_kod int4, vusc_kod int2, zmena_grafiky varchar(1), puvod int2
rn_orp_p (writer POSTGIS_1)
    attributes: id_trans_ruian int8, kod int2, nazev varchar(48), nespravny varchar(1), nz_id_globalni int8, plati_od timestamptz, spravni_obec_kod int4, vusc_kod int2, zmena_grafiky varchar(1), puvod int2
rn_parcela_b (writer POSTGIS_1)
    attributes: orientation numeric(6,3), z numeric(20,8), druh_cislovani_kod int2, druh_pozemku_kod int2, id int8, id_trans_ruian int8, katuz_kod int4, kmenove_cislo int4, nespravny varchar(1), plati_od timestamptz, poddeleni_cisla int2, rizeni_id int8, vymera_parcely int8, zpusob_vyu_poz_kod int2, puvod int2
rn_parcela_p (writer POSTGIS_1)
    attributes: druh_cislovani_kod int2, druh_pozemku_kod int2, id int8, id_trans_ruian int8, katuz_kod int4, kmenove_cislo int4, nespravny varchar(1), plati_od timestamptz, poddeleni_cisla int2, rizeni_id int8, vymera_parcely int8, zpusob_vyu_poz_kod int2, puvod int2
rn_bonit_dily_parcel (writer POSTGRES_1)
    attributes: bpej_kod int4,BTree, id_trans_ruian int8, parcela_id int8,BTree, rizeni_id int8, vymera int4, puvod int2
rn_zpusob_ochrany_pozemku (writer POSTGRES_1)
    attributes: id_trans_ruian int8, parcela_id int8,BTree, rizeni_id int8, zpusob_ochrany_kod int2,BTree, puvod int2
rn_pou_b (writer POSTGIS_1)
    attributes: orientation numeric(6,3), id_trans_ruian int8, kod int2, nazev numeric(48,10), nespravny varchar(1), nz_id_globalni int8, orp_kod int2, plati_od timestamptz, spravni_obec_kod int4, zmena_grafiky varchar(1), puvod int2
rn_pou_p (writer POSTGIS_1)
    attributes: id_trans_ruian int8, kod int8, nazev varchar(48), nespravny varchar(1), nz_id_globalni int8, orp_kod int2, plati_od timestamptz, spravni_obec_kod int4, zmena_grafiky varchar(1), puvod int2
rn_region_soudrznosti_b (writer POSTGIS_1)
    attributes: orientation numeric(6,3), id_trans_ruian int8, kod int2, nazev numeric(32,10), nespravny varchar(1), nuts_lau varchar(6), nz_id_globalni int8, plati_od timestamptz, stat_kod int2, zmena_grafiky varchar(1), puvod int2
rn_region_soudrznosti_p (writer POSTGIS_1)
    attributes: id_trans_ruian int8, kod int8, nazev varchar(32), nespravny varchar(1), nuts_lau varchar(6), nz_id_globalni int8, plati_od timestamptz, stat_kod int2, zmena_grafiky varchar(1), puvod int2
rn_spravni_obvod_b (writer POSTGIS_1)
    attributes: orientation numeric(6,3), id_trans_ruian int8, kod int2, nazev varchar(32), nespravny varchar(1), nz_id_globalni int8, obec_kod int4, plati_od timestamptz, spravni_momc_kod int4, zmena_grafiky varchar(1), puvod int2
rn_spravni_obvod_p (writer POSTGIS_1)
    attributes: id_trans_ruian int8, kod int8, nazev varchar(32), nespravny varchar(1), nz_id_globalni int8, obec_kod int4, plati_od timestamptz, spravni_momc_kod int4, zmena_grafiky varchar(1), puvod int2
rn_stat_b (writer POSTGIS_1)
    attributes: orientation numeric(6,3), id_trans_ruian int8, kod int2, nazev numeric(32,10), nespravny varchar(1), nuts_lau varchar(6), nz_id_globalni int8, plati_od timestamptz, zmena_grafiky varchar(1), puvod int2
rn_stat_p (writer POSTGIS_1)
    attributes: id_trans_ruian int8, kod int8, nazev varchar(32), nespravny varchar(1), nuts_lau varchar(6), nz_id_globalni int8, plati_od timestamptz, zmena_grafiky varchar(1), puvod int2
rn_stavebni_objekt_b (writer POSTGIS_1)
    attributes: budova_id int8, orientation numeric(6,3), cobce_kod int4, dokonceni numeric(20,10), druh_konstrukce_kod int2, id_trans_ruian int8, identifikacni_parcela_id int8, je_vytah_kod int2, kod int4, momc_kod int4, nespravny varchar(1), nz_id_globalni int8, obestaveny_prostor int4, plati_od timestamptz, pocet_bytu int2, pocet_podlazi int2, podlahova_plocha int4, pripoj_kanal_sit_kod int2, pripoj_plyn_kod int2, pripoj_vodovod_kod int2, typ_kod int2, zastavena_plocha int4, zmena_grafiky varchar(1), zpusob_vytapeni_kod int2, zpusob_vyuziti_kod int2, puvod int2
rn_stavebni_objekt_p (writer POSTGIS_1)
    attributes: budova_id int8, cobce_kod int8, dokonceni timestamptz, druh_konstrukce_kod int2, id_trans_ruian int8, identifikacni_parcela_id int8, je_vytah_kod int2, kod int4, momc_kod int4, nespravny varchar(1), nz_id_globalni int8, obestaveny_prostor int4, plati_od timestamptz, pocet_bytu int2, pocet_podlazi int2, podlahova_plocha int4, pripoj_kanal_sit_kod int2, pripoj_plyn_kod int2, pripoj_vodovod_kod int2, typ_kod int2, zastavena_plocha int4, zmena_grafiky varchar(1), zpusob_vytapeni_kod int2, zpusob_vyuziti_kod int2, puvod int2
rn_detailni_tea (writer POSTGRES_1)
    attributes: druh_konstrukce_kod int2,BTree, kod int4,BTree, nespravny varchar(1), nz_id_globalni int8, plati_od timestamptz, pocet_bytu int2, pocet_podlazi int2, pripoj_kanal_sit_kod int2,BTree, pripoj_plyn_kod int2,BTree, pripoj_vodovod_kod int2,BTree, stavobj_kod int4,BTree, zpusob_vytapeni_kod int2,BTree, puvod int2
rn_ulice_l (writer POSTGIS_1)
    attributes: id_trans_ruian int8, kod int8, nazev varchar(48), nespravny varchar(1), nz_id_globalni int8, obec_kod int4, plati_od timestamptz, zmena_grafiky varchar(1), puvod int2
rn_vusc_b (writer POSTGIS_1)
    attributes: orientation numeric(6,3), id_trans_ruian int8, kod int2, nazev numeric(32,10), nespravny varchar(1), nuts_lau varchar(6), nz_id_globalni int8, plati_od timestamptz, regsoudr_kod int2, zmena_grafiky varchar(1), puvod int2
rn_vusc_p (writer POSTGIS_1)
    attributes: id_trans_ruian int8, kod int8, nazev varchar(32), nespravny varchar(1), nuts_lau varchar(6), nz_id_globalni int8, plati_od timestamptz, regsoudr_kod int2, zmena_grafiky varchar(1), puvod int2
rn_zsj_b (writer POSTGIS_1)
    attributes: orientation numeric(6,3), charakter_zsj_kod int2, id_trans_ruian int8, katuz_kod int4, kod int4, mluv_char_pad_2 varchar(48), mluv_char_pad_3 varchar(48), mluv_char_pad_4 varchar(48), mluv_char_pad_5 varchar(48), mluv_char_pad_6 varchar(48), mluv_char_pad_7 varchar(48), nazev varchar(48), nespravny varchar(1), nz_id_globalni int8, plati_od timestamptz, vymera int8, zmena_grafiky varchar(1), puvod int2
rn_zsj_p (writer POSTGIS_1)
    attributes: charakter_zsj_kod int2, id_trans_ruian int2, katuz_kod int4, kod int4, mluv_char_pad_2 varchar(48), mluv_char_pad_3 varchar(48), mluv_char_pad_4 varchar(48), mluv_char_pad_5 varchar(48), mluv_char_pad_6 varchar(48), mluv_char_pad_7 varchar(48), nazev varchar(48), nespravny varchar(1), nz_id_globalni int8, plati_od timestamptz, vymera int8, zmena_grafiky varchar(1), puvod int2
rn_zpusob_ochrany_objektu (writer POSTGRES_1)
    attributes: id_trans_ruian int8, rizeni_id int8, stavobj_kod int4,BTree, zpusob_ochrany_kod int2,BTree, puvod int2

Bookmark: CAST OBCE
AttributeKeeper_2
    CREATE_BULK_MODE_FEATURES = NO
    KEEP_ATTRS = GlobalniIdNavrhuZmeny,IdTransakce,Kod,Nespravny,PlatiDo,PlatiOd,MluvnickeCharakteristiky.Pad2,MluvnickeCharakteristiky.Pad3,MluvnickeCharakteristiky.Pad4,MluvnickeCharakteristiky.Pad5,MluvnickeCharakteristiky.Pad6,MluvnickeCharakteristiky.Pad7,Nazev,Obec.Kod
    -> DateTimeConverter_2
DateTimeConverter_2
    DATETIME_ATTR = PlatiDo PlatiOd
    IN_FORMAT = ISO
    OUT_FORMAT = FME
    PASSTHROUGH = YES
    REPAIR_INPUT = NO
    TEST_INPUT = 2013-12-05T00:00:00
    -> AttributeManager_2
AttributeManager_2
    ATTR_TABLE:
      SET_TO ZMENA_GRAFIKY = N
      SET_TO PUVOD = 1
      SET_TO PLATI_OD = @TimeZoneSet(@Value(PlatiOd),+01:00,auto)
      SET_TO ORIENTATION = 90
      SET_TO ID_TRANS_RUIAN = @Value(IdTransakce)
      SET_TO NZ_ID_GLOBALNI = @Value(GlobalniIdNavrhuZmeny)
      RENAME_SET_VALUE Kod > KOD
      RENAME_SET_VALUE Nespravny > NESPRAVNY = FME_CONDITIONAL:DEFAULT_VALUE'FME_NULL_VALUE'BOOL_OP;OR;COMPOSITE_TEST;1;TEST @Value(Nespravny) = true'1'FME_NUM_CONDITIONS2___
      REMOVE PlatiOd
      RENAME_SET_VALUE PlatiDo > PLATI_DO
      RENAME_SET_VALUE IdTransakce > ID_TRANS_RUIAN
      RENAME_SET_VALUE GlobalniIdNavrhuZmeny > NZ_ID_GLOBALNI
      RENAME_SET_VALUE Nazev > NAZEV
      RENAME_SET_VALUE Obec.Kod > OBEC_KOD
      RENAME_SET_VALUE MluvnickeCharakteristiky.Pad2 > MLUV_CHAR_PAD_2
      RENAME_SET_VALUE MluvnickeCharakteristiky.Pad3 > MLUV_CHAR_PAD_3
      RENAME_SET_VALUE MluvnickeCharakteristiky.Pad4 > MLUV_CHAR_PAD_4
      RENAME_SET_VALUE MluvnickeCharakteristiky.Pad5 > MLUV_CHAR_PAD_5
      RENAME_SET_VALUE MluvnickeCharakteristiky.Pad6 > MLUV_CHAR_PAD_6
      RENAME_SET_VALUE MluvnickeCharakteristiky.Pad7 > MLUV_CHAR_PAD_7
    -> TestFilter_3

Bookmark: KATASTRALNI UZEMI
AttributeKeeper_3
    CREATE_BULK_MODE_FEATURES = NO
    KEEP_ATTRS = GlobalniIdNavrhuZmeny,IdTransakce,Kod,Nespravny,PlatiDo,PlatiOd,MluvnickeCharakteristiky.Pad2,MluvnickeCharakteristiky.Pad3,MluvnickeCharakteristiky.Pad4,MluvnickeCharakteristiky.Pad5,MluvnickeCharakteristiky.Pad6,MluvnickeCharakteristiky.Pad7,Nazev,Obec.Kod,ExistujeDigitalniMapa,RizeniId
    -> DateTimeConverter_3
DateTimeConverter_3
    DATETIME_ATTR = PlatiDo PlatiOd
    IN_FORMAT = ISO
    OUT_FORMAT = FME
    PASSTHROUGH = YES
    REPAIR_INPUT = NO
    TEST_INPUT = 2013-12-05T00:00:00
    -> AttributeManager_3
AttributeManager_3
    ATTR_TABLE:
      SET_TO ZMENA_GRAFIKY = N
      SET_TO PUVOD = 1
      SET_TO PLATI_OD = @TimeZoneSet(@Value(PlatiOd),+01:00,auto)
      SET_TO ORIENTATION = 90
      SET_TO ID_TRANS_RUIAN = @Value(IdTransakce)
      SET_TO NZ_ID_GLOBALNI = @Value(GlobalniIdNavrhuZmeny)
      RENAME_SET_VALUE Kod > KOD
      RENAME_SET_VALUE Nespravny > NESPRAVNY = FME_CONDITIONAL:DEFAULT_VALUE'FME_NULL_VALUE'BOOL_OP;OR;COMPOSITE_TEST;1;TEST @Value(Nespravny) = true'1'FME_NUM_CONDITIONS2___
      REMOVE PlatiOd
      RENAME_SET_VALUE PlatiDo > PLATI_DO
      RENAME_SET_VALUE IdTransakce > ID_TRANS_RUIAN
      RENAME_SET_VALUE GlobalniIdNavrhuZmeny > NZ_ID_GLOBALNI
      RENAME_SET_VALUE Nazev > NAZEV
      RENAME_SET_VALUE Obec.Kod > OBEC_KOD
      RENAME_SET_VALUE MluvnickeCharakteristiky.Pad2 > MLUV_CHAR_PAD_2
      RENAME_SET_VALUE MluvnickeCharakteristiky.Pad3 > MLUV_CHAR_PAD_3
      RENAME_SET_VALUE MluvnickeCharakteristiky.Pad4 > MLUV_CHAR_PAD_4
      RENAME_SET_VALUE MluvnickeCharakteristiky.Pad5 > MLUV_CHAR_PAD_5
      RENAME_SET_VALUE MluvnickeCharakteristiky.Pad6 > MLUV_CHAR_PAD_6
      RENAME_SET_VALUE MluvnickeCharakteristiky.Pad7 > MLUV_CHAR_PAD_7
      RENAME_SET_VALUE ExistujeDigitalniMapa > MA_DKM = FME_CONDITIONAL:DEFAULT_VALUE'N'BOOL_OP;OR;COMPOSITE_TEST;1;TEST @Value(ExistujeDigitalniMapa) = true'A'FME_NUM_CONDITIONS2___
      RENAME_SET_VALUE RizeniId > RIZENI_ID
    -> GeometryFilter
GeometryFilter
    FILTER_MODE = SIMPLE
    FILTER_MULTI = FILTER_TYPES]"Point Area"]FME_CONTROLLER_QUERY_FILE]]FME_CONTROLLER_CHOICE]Simple
    Point -> GeometryRefiner
    Area -> GeometryRefiner_35
GeometryRefiner
    -> GeometryFilter_28
GeometryFilter_28
    FILTER_MODE = COMPLETE
    FILTER_MULTI = FILTER_TYPES]"MultiPoint Point"]INSTANCES]INSTANCE]FME_CONTROLLER_QUERY_FILE]]FME_CONTROLLER_CHOICE]Complete
    Point -> Aggregator_15
    MultiPoint -> TestFilter_4
Aggregator_15
    ACCUM_ATTRS_NAME = Use Attributes From One Feature
    AGGREGATE_TYPE = Homogeneous Collection (If Possible)
    GROUP_BY = KOD
    MODE = Geometry - Assemble One Level
    SEP = ,
    AGGREGATE -> TestFilter_4
GeometryRefiner_35
    -> GeometryExtractor_13
GeometryExtractor_13
    ATTR = _geometry
    KIND_LONG = OGC Well Known Text
    OGCVERSION = 1.2
    OGC_WKT_PRECISION_DISPLAY = 64-bit
    REMOVE_GEOMETRY = No
    -> GeometryReplacer_13
GeometryReplacer_13
    KIND_LONG = OGC Well Known Text
    OGC_WKT_PRECISION_DISPLAY = 64-bit
    REMOVE_ATTRIBUTE = Yes
    SOURCE = @Value(_geometry)
    -> Aggregator_13
Aggregator_13
    ACCUM_ATTRS_NAME = Use Attributes From One Feature
    AGGREGATE_TYPE = Homogeneous Collection (If Possible)
    GROUP_BY = KOD
    MODE = Geometry - Assemble One Level
    SEP = ,
    AGGREGATE -> GeometryFilter_29
GeometryFilter_29
    FILTER_MODE = COMPLETE
    FILTER_MULTI = FILTER_TYPES]"Aggregate MultiArea"]INSTANCES]INSTANCE]FME_CONTROLLER_QUERY_FILE]]FME_CONTROLLER_CHOICE]Complete
    MultiArea -> TestFilter_5
    Aggregate -> GeometryRefiner_37
GeometryRefiner_37
    -> TestFilter_5

Bookmark: MOMC - MESTSKY OBVOD, MESTSKA CAST
AttributeKeeper_15
    CREATE_BULK_MODE_FEATURES = NO
    KEEP_ATTRS = IdTransakce,Nespravny,PlatiDo,PlatiOd,GlobalniIdNavrhuZmeny,Kod,Nazev,MluvnickeCharakteristiky.Pad2,MluvnickeCharakteristiky.Pad3,MluvnickeCharakteristiky.Pad4,MluvnickeCharakteristiky.Pad5,MluvnickeCharakteristiky.Pad6,MluvnickeCharakteristiky.Pad7,Mop.Kod,Obec.Kod,Obec.Pou.Kod,SpravniObvod.Kod,VlajkaObrazek,VlajkaText,ZnakObrazek,ZnakText
    -> DateTimeConverter_15
DateTimeConverter_15
    DATETIME_ATTR = PlatiDo PlatiOd
    IN_FORMAT = ISO
    OUT_FORMAT = FME
    PASSTHROUGH = YES
    REPAIR_INPUT = NO
    TEST_INPUT = 2013-12-05T00:00:00
    -> AttributeManager_4
AttributeManager_4
    ATTR_TABLE:
      SET_TO ZMENA_GRAFIKY = N
      SET_TO PUVOD = 1
      SET_TO PLATI_OD = @TimeZoneSet(@Value(PlatiOd),+01:00,auto)
      SET_TO ORIENTATION = 90
      SET_TO ID_TRANS_RUIAN = @Value(IdTransakce)
      SET_TO NZ_ID_GLOBALNI = @Value(GlobalniIdNavrhuZmeny)
      RENAME_SET_VALUE Kod > KOD
      RENAME_SET_VALUE Nespravny > NESPRAVNY = FME_CONDITIONAL:DEFAULT_VALUE'FME_NULL_VALUE'BOOL_OP;OR;COMPOSITE_TEST;1;TEST @Value(Nespravny) = true'1'FME_NUM_CONDITIONS2___
      REMOVE PlatiOd
      RENAME_SET_VALUE PlatiDo > PLATI_DO
      RENAME_SET_VALUE IdTransakce > ID_TRANS_RUIAN
      RENAME_SET_VALUE GlobalniIdNavrhuZmeny > NZ_ID_GLOBALNI
      RENAME_SET_VALUE Nazev > NAZEV
      RENAME_SET_VALUE Obec.Kod > OBEC_KOD
      RENAME_SET_VALUE MluvnickeCharakteristiky.Pad2 > MLUV_CHAR_PAD_2
      RENAME_SET_VALUE MluvnickeCharakteristiky.Pad3 > MLUV_CHAR_PAD_3
      RENAME_SET_VALUE MluvnickeCharakteristiky.Pad4 > MLUV_CHAR_PAD_4
      RENAME_SET_VALUE MluvnickeCharakteristiky.Pad5 > MLUV_CHAR_PAD_5
      RENAME_SET_VALUE MluvnickeCharakteristiky.Pad6 > MLUV_CHAR_PAD_6
      RENAME_SET_VALUE MluvnickeCharakteristiky.Pad7 > MLUV_CHAR_PAD_7
      RENAME_SET_VALUE Mop.Kod > MOP_KOD
      RENAME_SET_VALUE Obec.Pou.Kod > POU_KOD
      RENAME_SET_VALUE SpravniObvod.Kod > SPRAVOBV_KOD
      RENAME_SET_VALUE VlajkaText > VLAJKA_TEXT
      RENAME_SET_VALUE VlajkaObrazek > VLAJKA_OBRAZEK
      RENAME_SET_VALUE ZnakText > ZNAK_TEXT
      RENAME_SET_VALUE ZnakObrazek > ZNAK_OBRAZEK
    -> GeometryFilter_18
GeometryFilter_18
    FILTER_MODE = SIMPLE
    FILTER_MULTI = FILTER_TYPES]"Point Area"]FME_CONTROLLER_QUERY_FILE]]FME_CONTROLLER_CHOICE]Simple
    Point -> GeometryRefiner_25
    Area -> GeometryRefiner_26
GeometryRefiner_25
    -> TestFilter_6
GeometryRefiner_26
    -> GeometryExtractor_9
GeometryExtractor_9
    ATTR = _geometry
    KIND_LONG = OGC Well Known Text
    OGCVERSION = 1.2
    OGC_WKT_PRECISION_DISPLAY = 64-bit
    REMOVE_GEOMETRY = No
    -> GeometryReplacer_9
GeometryReplacer_9
    KIND_LONG = OGC Well Known Text
    OGC_WKT_PRECISION_DISPLAY = 64-bit
    REMOVE_ATTRIBUTE = Yes
    SOURCE = @Value(_geometry)
    -> Aggregator_9
Aggregator_9
    ACCUM_ATTRS_NAME = Use Attributes From One Feature
    AGGREGATE_TYPE = Homogeneous Collection (If Possible)
    GROUP_BY = KOD
    MODE = Geometry - Assemble One Level
    SEP = ,
    AGGREGATE -> GeometryFilter_19
GeometryFilter_19
    FILTER_MODE = COMPLETE
    FILTER_MULTI = FILTER_TYPES]"Aggregate MultiArea"]INSTANCES]INSTANCE]FME_CONTROLLER_QUERY_FILE]]FME_CONTROLLER_CHOICE]Complete
    MultiArea -> TestFilter_7
    Aggregate -> GeometryRefiner_27
GeometryRefiner_27
    -> TestFilter_7

Bookmark: MOP - OBVOD PRAHY
AttributeKeeper_16
    CREATE_BULK_MODE_FEATURES = NO
    KEEP_ATTRS = IdTransakce,Nespravny,PlatiDo,PlatiOd,GlobalniIdNavrhuZmeny,Kod,Nazev,MluvnickeCharakteristiky.Pad2,MluvnickeCharakteristiky.Pad3,MluvnickeCharakteristiky.Pad4,MluvnickeCharakteristiky.Pad5,MluvnickeCharakteristiky.Pad6,MluvnickeCharakteristiky.Pad7,Mop.Kod,Obec.Kod,Obec.Pou.Kod,SpravniObvod.Kod,VlajkaObrazek,VlajkaText,ZnakObrazek,ZnakText
    -> DateTimeConverter_16
DateTimeConverter_16
    DATETIME_ATTR = PlatiDo PlatiOd
    IN_FORMAT = ISO
    OUT_FORMAT = FME
    PASSTHROUGH = YES
    REPAIR_INPUT = NO
    TEST_INPUT = 2013-12-05T00:00:00
    -> AttributeManager_5
AttributeManager_5
    ATTR_TABLE:
      SET_TO ZMENA_GRAFIKY = N
      SET_TO PUVOD = 1
      SET_TO PLATI_OD = @TimeZoneSet(@Value(PlatiOd),+01:00,auto)
      SET_TO ORIENTATION = 90
      SET_TO ID_TRANS_RUIAN = @Value(IdTransakce)
      SET_TO NZ_ID_GLOBALNI = @Value(GlobalniIdNavrhuZmeny)
      RENAME_SET_VALUE Kod > KOD
      RENAME_SET_VALUE Nespravny > NESPRAVNY = FME_CONDITIONAL:DEFAULT_VALUE'FME_NULL_VALUE'BOOL_OP;OR;COMPOSITE_TEST;1;TEST @Value(Nespravny) = true'1'FME_NUM_CONDITIONS2___
      REMOVE PlatiOd
      RENAME_SET_VALUE PlatiDo > PLATI_DO
      RENAME_SET_VALUE IdTransakce > ID_TRANS_RUIAN
      RENAME_SET_VALUE GlobalniIdNavrhuZmeny > NZ_ID_GLOBALNI
      RENAME_SET_VALUE Nazev > NAZEV
      RENAME_SET_VALUE Obec.Kod > OBEC_KOD
      RENAME_SET_VALUE Obec.Pou.Kod > POU_KOD
    -> GeometryFilter_20
GeometryFilter_20
    FILTER_MODE = SIMPLE
    FILTER_MULTI = FILTER_TYPES]"Point Area"]FME_CONTROLLER_QUERY_FILE]]FME_CONTROLLER_CHOICE]Simple
    Point -> GeometryRefiner_28
    Area -> GeometryRefiner_29
GeometryRefiner_28
    -> TestFilter_8
GeometryRefiner_29
    -> GeometryExtractor_10
GeometryExtractor_10
    ATTR = _geometry
    KIND_LONG = OGC Well Known Text
    OGCVERSION = 1.2
    OGC_WKT_PRECISION_DISPLAY = 64-bit
    REMOVE_GEOMETRY = No
    -> GeometryReplacer_10
GeometryReplacer_10
    KIND_LONG = OGC Well Known Text
    OGC_WKT_PRECISION_DISPLAY = 64-bit
    REMOVE_ATTRIBUTE = Yes
    SOURCE = @Value(_geometry)
    -> Aggregator_10
Aggregator_10
    ACCUM_ATTRS_NAME = Use Attributes From One Feature
    AGGREGATE_TYPE = Homogeneous Collection (If Possible)
    GROUP_BY = KOD
    MODE = Geometry - Assemble One Level
    SEP = ,
    AGGREGATE -> GeometryFilter_21
GeometryFilter_21
    FILTER_MODE = COMPLETE
    FILTER_MULTI = FILTER_TYPES]"Aggregate MultiArea"]INSTANCES]INSTANCE]FME_CONTROLLER_QUERY_FILE]]FME_CONTROLLER_CHOICE]Complete
    MultiArea -> TestFilter_9
    Aggregate -> GeometryRefiner_30
GeometryRefiner_30
    -> TestFilter_9

Bookmark: OBEC
AttributeKeeper_4
    CREATE_BULK_MODE_FEATURES = NO
    KEEP_ATTRS = GlobalniIdNavrhuZmeny,IdTransakce,Kod,Nespravny,PlatiDo,PlatiOd,MluvnickeCharakteristiky.Pad2,MluvnickeCharakteristiky.Pad3,MluvnickeCharakteristiky.Pad4,MluvnickeCharakteristiky.Pad5,MluvnickeCharakteristiky.Pad6,MluvnickeCharakteristiky.Pad7,Nazev,Okres.Kod,ZnakObrazek,ZnakText,Pou.Kod,VlajkaObrazek,VlajkaText,StatusKod,CleneniSMRozsahKod,CleneniSMTypKod
    -> DateTimeConverter_4
DateTimeConverter_4
    DATETIME_ATTR = PlatiDo PlatiOd
    IN_FORMAT = ISO
    OUT_FORMAT = FME
    PASSTHROUGH = YES
    REPAIR_INPUT = NO
    TEST_INPUT = 2013-12-05T00:00:00
    -> AttributeManager_6
AttributeManager_6
    ATTR_TABLE:
      SET_TO ZMENA_GRAFIKY = N
      SET_TO PUVOD = 1
      SET_TO PLATI_OD = @TimeZoneSet(@Value(PlatiOd),+01:00,auto)
      SET_TO ORIENTATION = 90
      SET_TO ID_TRANS_RUIAN = @Value(IdTransakce)
      SET_TO NZ_ID_GLOBALNI = @Value(GlobalniIdNavrhuZmeny)
      RENAME_SET_VALUE Kod > KOD
      RENAME_SET_VALUE Nespravny > NESPRAVNY = FME_CONDITIONAL:DEFAULT_VALUE'FME_NULL_VALUE'BOOL_OP;OR;COMPOSITE_TEST;1;TEST @Value(Nespravny) = true'1'FME_NUM_CONDITIONS2___
      REMOVE PlatiOd
      RENAME_SET_VALUE PlatiDo > PLATI_DO
      RENAME_SET_VALUE IdTransakce > ID_TRANS_RUIAN
      RENAME_SET_VALUE GlobalniIdNavrhuZmeny > NZ_ID_GLOBALNI
      RENAME_SET_VALUE Nazev > NAZEV
      RENAME_SET_VALUE MluvnickeCharakteristiky.Pad2 > MLUV_CHAR_PAD_2
      RENAME_SET_VALUE MluvnickeCharakteristiky.Pad3 > MLUV_CHAR_PAD_3
      RENAME_SET_VALUE MluvnickeCharakteristiky.Pad4 > MLUV_CHAR_PAD_4
      RENAME_SET_VALUE MluvnickeCharakteristiky.Pad5 > MLUV_CHAR_PAD_5
      RENAME_SET_VALUE MluvnickeCharakteristiky.Pad6 > MLUV_CHAR_PAD_6
      RENAME_SET_VALUE MluvnickeCharakteristiky.Pad7 > MLUV_CHAR_PAD_7
      RENAME_SET_VALUE VlajkaText > VLAJKA_TEXT
      RENAME_SET_VALUE VlajkaObrazek > VLAJKA_OBRAZEK
      RENAME_SET_VALUE ZnakText > ZNAK_TEXT
      RENAME_SET_VALUE ZnakObrazek > ZNAK_OBRAZEK
      RENAME_SET_VALUE StatusKod > STATUS_KOD
      RENAME_SET_VALUE Okres.Kod > OKRES_KOD
      RENAME_SET_VALUE Pou.Kod > POU_KOD
      RENAME_SET_VALUE CleneniSMRozsahKod > CLENENI_SM_ROZSAH_KOD
      RENAME_SET_VALUE CleneniSMTypKod > CLENENI_SM_TYP_KOD
    -> GeometryFilter_2
GeometryFilter_2
    FILTER_MODE = SIMPLE
    FILTER_MULTI = FILTER_TYPES]"Point Area"]FME_CONTROLLER_QUERY_FILE]]FME_CONTROLLER_CHOICE]Simple
    Point -> GeometryRefiner_2
    Area -> GeometryExtractor_12
GeometryRefiner_2
    -> TestFilter_10
GeometryExtractor_12
    ATTR = _geometry
    KIND_LONG = OGC Well Known Text
    OGCVERSION = 1.2
    OGC_WKT_PRECISION_DISPLAY = 64-bit
    REMOVE_GEOMETRY = No
    -> GeometryReplacer_12
GeometryReplacer_12
    KIND_LONG = OGC Well Known Text
    OGC_WKT_PRECISION_DISPLAY = 64-bit
    REMOVE_ATTRIBUTE = Yes
    SOURCE = @Value(_geometry)
    -> Aggregator_12
Aggregator_12
    ACCUM_ATTRS_NAME = Use Attributes From One Feature
    AGGREGATE_TYPE = Homogeneous Collection (If Possible)
    GROUP_BY = KOD
    MODE = Geometry - Assemble One Level
    SEP = ,
    AGGREGATE -> GeometryFilter_24
GeometryFilter_24
    FILTER_MODE = COMPLETE
    FILTER_MULTI = FILTER_TYPES]"Aggregate MultiArea"]INSTANCES]INSTANCE]FME_CONTROLLER_QUERY_FILE]]FME_CONTROLLER_CHOICE]Complete
    MultiArea -> TestFilter_11
    Aggregate -> GeometryRefiner_34
GeometryRefiner_34
    -> TestFilter_11

Bookmark: OKRES
AttributeKeeper_9
    CREATE_BULK_MODE_FEATURES = NO
    KEEP_ATTRS = IdTransakce,Nespravny,PlatiDo,PlatiOd,GlobalniIdNavrhuZmeny,Kod,Nazev,NutsLau,Vusc.Kod
    -> DateTimeConverter_9
DateTimeConverter_9
    DATETIME_ATTR = PlatiDo PlatiOd
    IN_FORMAT = ISO
    OUT_FORMAT = FME
    PASSTHROUGH = YES
    REPAIR_INPUT = NO
    TEST_INPUT = 2013-12-05T00:00:00
    -> AttributeManager_7
AttributeManager_7
    ATTR_TABLE:
      SET_TO ZMENA_GRAFIKY = N
      SET_TO PUVOD = 1
      SET_TO PLATI_OD = @TimeZoneSet(@Value(PlatiOd),+01:00,auto)
      SET_TO ORIENTATION = 90
      SET_TO ID_TRANS_RUIAN = @Value(IdTransakce)
      SET_TO NZ_ID_GLOBALNI = @Value(GlobalniIdNavrhuZmeny)
      RENAME_SET_VALUE Kod > KOD
      RENAME_SET_VALUE Nespravny > NESPRAVNY = FME_CONDITIONAL:DEFAULT_VALUE'FME_NULL_VALUE'BOOL_OP;OR;COMPOSITE_TEST;1;TEST @Value(Nespravny) = true'1'FME_NUM_CONDITIONS2___
      REMOVE PlatiOd
      RENAME_SET_VALUE PlatiDo > PLATI_DO
      RENAME_SET_VALUE IdTransakce > ID_TRANS_RUIAN
      RENAME_SET_VALUE GlobalniIdNavrhuZmeny > NZ_ID_GLOBALNI
      RENAME_SET_VALUE Nazev > NAZEV
      RENAME_SET_VALUE Vusc.Kod > VUSC_KOD
      RENAME_SET_VALUE NutsLau > NUTS_LAU
    -> GeometryFilter_7
GeometryFilter_7
    FILTER_MODE = SIMPLE
    FILTER_MULTI = FILTER_TYPES]"Point Area"]FME_CONTROLLER_QUERY_FILE]]FME_CONTROLLER_CHOICE]Simple
    Point -> GeometryRefiner_9
    Area -> GeometryExtractor_4
GeometryRefiner_9
    -> TestFilter_12
GeometryExtractor_4
    ATTR = _geometry
    KIND_LONG = OGC Well Known Text
    OGCVERSION = 1.2
    OGC_WKT_PRECISION_DISPLAY = 64-bit
    REMOVE_GEOMETRY = No
    -> GeometryReplacer_4
GeometryReplacer_4
    KIND_LONG = OGC Well Known Text
    OGC_WKT_PRECISION_DISPLAY = 64-bit
    REMOVE_ATTRIBUTE = Yes
    SOURCE = @Value(_geometry)
    -> Aggregator_3
Aggregator_3
    ACCUM_ATTRS_NAME = Use Attributes From One Feature
    AGGREGATE_TYPE = Homogeneous Collection (If Possible)
    GROUP_BY = KOD
    MODE = Geometry - Assemble One Level
    SEP = ,
    AGGREGATE -> GeometryFilter_8
GeometryFilter_8
    FILTER_MODE = COMPLETE
    FILTER_MULTI = FILTER_TYPES]"Aggregate Area MultiArea"]INSTANCES]INSTANCE]FME_CONTROLLER_QUERY_FILE]]FME_CONTROLLER_CHOICE]Complete
    MultiArea -> TestFilter_13
    Aggregate -> GeometryRefiner_10
GeometryRefiner_10
    -> TestFilter_13

Bookmark: ORP - OBEC S ROZSIRENOU PUSOBNOSTI
AttributeKeeper_10
    CREATE_BULK_MODE_FEATURES = NO
    KEEP_ATTRS = GlobalniIdNavrhuZmeny,IdTransakce,Kod,Nespravny,PlatiDo,PlatiOd,Nazev,SpravniObecKod,Vusc.Kod
    -> DateTimeConverter_10
DateTimeConverter_10
    DATETIME_ATTR = PlatiDo PlatiOd
    IN_FORMAT = ISO
    OUT_FORMAT = FME
    PASSTHROUGH = YES
    REPAIR_INPUT = NO
    TEST_INPUT = 2013-12-05T00:00:00
    -> AttributeManager_8
AttributeManager_8
    ATTR_TABLE:
      SET_TO ZMENA_GRAFIKY = N
      SET_TO PUVOD = 1
      SET_TO PLATI_OD = @TimeZoneSet(@Value(PlatiOd),+01:00,auto)
      SET_TO ORIENTATION = 90
      SET_TO ID_TRANS_RUIAN = @Value(IdTransakce)
      SET_TO NZ_ID_GLOBALNI = @Value(GlobalniIdNavrhuZmeny)
      RENAME_SET_VALUE Kod > KOD
      RENAME_SET_VALUE Nespravny > NESPRAVNY = FME_CONDITIONAL:DEFAULT_VALUE'FME_NULL_VALUE'BOOL_OP;OR;COMPOSITE_TEST;1;TEST @Value(Nespravny) = true'1'FME_NUM_CONDITIONS2___
      REMOVE PlatiOd
      RENAME_SET_VALUE PlatiDo > PLATI_DO
      RENAME_SET_VALUE IdTransakce > ID_TRANS_RUIAN
      RENAME_SET_VALUE GlobalniIdNavrhuZmeny > NZ_ID_GLOBALNI
      RENAME_SET_VALUE Nazev > NAZEV
      RENAME_SET_VALUE Vusc.Kod > VUSC_KOD
      RENAME_SET_VALUE SpravniObecKod > SPRAVNI_OBEC_KOD
    -> GeometryFilter_9
GeometryFilter_9
    FILTER_MODE = SIMPLE
    FILTER_MULTI = FILTER_TYPES]"Point Area"]FME_CONTROLLER_QUERY_FILE]]FME_CONTROLLER_CHOICE]Simple
    Point -> GeometryRefiner_11
    Area -> GeometryRefiner_12
GeometryRefiner_11
    -> TestFilter_14
GeometryRefiner_12
    -> GeometryExtractor_5
GeometryExtractor_5
    ATTR = _geometry
    KIND_LONG = OGC Well Known Text
    OGCVERSION = 1.2
    OGC_WKT_PRECISION_DISPLAY = 64-bit
    REMOVE_GEOMETRY = No
    -> GeometryReplacer_5
GeometryReplacer_5
    KIND_LONG = OGC Well Known Text
    OGC_WKT_PRECISION_DISPLAY = 64-bit
    REMOVE_ATTRIBUTE = Yes
    SOURCE = @Value(_geometry)
    -> Aggregator_4
Aggregator_4
    ACCUM_ATTRS_NAME = Use Attributes From One Feature
    AGGREGATE_TYPE = Homogeneous Collection (If Possible)
    GROUP_BY = KOD
    MODE = Geometry - Assemble One Level
    SEP = ,
    AGGREGATE -> GeometryFilter_10
GeometryFilter_10
    FILTER_MODE = COMPLETE
    FILTER_MULTI = FILTER_TYPES]"Aggregate MultiArea"]INSTANCES]INSTANCE]FME_CONTROLLER_QUERY_FILE]]FME_CONTROLLER_CHOICE]Complete
    MultiArea -> TestFilter_15
    Aggregate -> GeometryRefiner_13
GeometryRefiner_13
    -> TestFilter_15

Bookmark: PARCELA
AttributeKeeper_5
    CREATE_BULK_MODE_FEATURES = NO
    KEEP_ATTRS = IdTransakce,Nespravny,PlatiDo,PlatiOd,DruhCislovaniKod,DruhPozemkuKod,Id,KmenoveCislo,PododdeleniCisla,RizeniId,VymeraParcely,ZpusobyVyuzitiPozemku,KatastralniUzemi.Kod
    -> DateTimeConverter_5
DateTimeConverter_5
    DATETIME_ATTR = PlatiDo PlatiOd
    IN_FORMAT = ISO
    OUT_FORMAT = FME
    PASSTHROUGH = YES
    REPAIR_INPUT = NO
    TEST_INPUT = 2013-12-05T00:00:00
    -> AttributeManager_9
AttributeManager_9
    ATTR_TABLE:
      SET_TO ZMENA_GRAFIKY = N
      SET_TO PUVOD = 1
      SET_TO PLATI_OD = @TimeZoneSet(@Value(PlatiOd),+01:00,auto)
      SET_TO ORIENTATION = 90
      SET_TO ID_TRANS_RUIAN = @Value(IdTransakce)
      RENAME_SET_VALUE Nespravny > NESPRAVNY = FME_CONDITIONAL:DEFAULT_VALUE'FME_NULL_VALUE'BOOL_OP;OR;COMPOSITE_TEST;1;TEST @Value(Nespravny) = true'1'FME_NUM_CONDITIONS2___
      REMOVE PlatiOd
      RENAME_SET_VALUE PlatiDo > PLATI_DO
      RENAME_SET_VALUE IdTransakce > ID_TRANS_RUIAN
      RENAME_SET_VALUE Id > ID
      RENAME_SET_VALUE KmenoveCislo > KMENOVE_CISLO
      RENAME_SET_VALUE PododdeleniCisla > PODDELENI_CISLA
      RENAME_SET_VALUE VymeraParcely > VYMERA_PARCELY
      RENAME_SET_VALUE ZpusobyVyuzitiPozemku > ZPUSOB_VYUZITI_KOD
      RENAME_SET_VALUE DruhCislovaniKod > DRUH_CISLOVANI_KOD
      RENAME_SET_VALUE DruhPozemkuKod > DRUH_POZEMKU_KOD
      RENAME_SET_VALUE KatastralniUzemi.Kod > KATUZ_KOD
      RENAME_SET_VALUE RizeniId > RIZENI_ID
      SET_TO ZPUSOB_VYU_POZ_KOD = @Value(ZPUSOB_VYUZITI_KOD)
    -> GeometryFilter_3
GeometryFilter_3
    FILTER_MODE = SIMPLE
    FILTER_MULTI = FILTER_TYPES]"Point Area Null"]FME_CONTROLLER_QUERY_FILE]]FME_CONTROLLER_CHOICE]Simple
    Null -> TestFilter_16
    Point -> GeometryRefiner_3
    Area -> GeometryRefiner_4
GeometryRefiner_3
    -> TestFilter_16
GeometryRefiner_4
    -> GeometryExtractor
GeometryExtractor
    ATTR = _geometry
    KIND_LONG = OGC Well Known Text
    OGCVERSION = 1.2
    OGC_WKT_PRECISION_DISPLAY = 64-bit
    REMOVE_GEOMETRY = No
    -> GeometryReplacer
GeometryReplacer
    KIND_LONG = OGC Well Known Text
    OGC_WKT_PRECISION_DISPLAY = 64-bit
    REMOVE_ATTRIBUTE = Yes
    SOURCE = @Value(_geometry)
    -> GeometryFilter_26
GeometryFilter_26
    FILTER_MODE = COMPLETE
    FILTER_MULTI = FILTER_TYPES]"Donut Polygon MultiArea"]INSTANCES]INSTANCE]FME_CONTROLLER_QUERY_FILE]]FME_CONTROLLER_CHOICE]Complete
    Polygon -> Aggregator_14
    Donut -> Aggregator_14
    MultiArea -> TestFilter_17
    <UNFILTERED> -> TestFilter_17
Aggregator_14
    ACCUM_ATTRS_NAME = Use Attributes From One Feature
    AGGREGATE_TYPE = Homogeneous Collection (If Possible)
    GROUP_BY = ID
    MODE = Geometry - Assemble One Level
    SEP = ,
    AGGREGATE -> TestFilter_17

Bookmark: Bonitovane dily parcel
Tester_3
    BOOL_OP = OR
    TEST_CLAUSE = TEST BonitovaneDily.BonitovanyDil{0}.BonitovanaJednotkaKod ATTRIBUTE_IS_MISSING ""
    TEST_MODE = TEST
    FAILED -> ListExploder_2
ListExploder_2
    ATTR_ACCUM_MODE = Merge List Attributes
    ATTR_CONFLICT_RES = Use List Attribute Values
    INDEX_ATTR = _element_index
    LIST_ATTR = BonitovaneDily.BonitovanyDil{}
    ELEMENTS -> AttributeKeeper_18
AttributeKeeper_18
    CREATE_BULK_MODE_FEATURES = NO
    KEEP_ATTRS = Id,BonitovanaJednotkaKod,IdTranskace,Vymera,RizeniId
    -> AttributeManager_14
AttributeManager_14
    ATTR_TABLE:
      SET_TO ZMENA_GRAFIKY = N
      SET_TO PUVOD = 1
      SET_TO ORIENTATION = 90
      RENAME_SET_VALUE Id > PARCELA_ID
      RENAME_SET_VALUE RizeniId > RIZENI_ID
      RENAME_SET_VALUE Vymera > VYMERA
      RENAME_SET_VALUE BonitovanaJednotkaKod > BPEJ_KOD
      RENAME_SET_VALUE IdTranskace > ID_TRANS_RUIAN
    -> TestFilter_32

Bookmark: Způsob ochrany parcel
Tester_6
    BOOL_OP = OR
    TEST_CLAUSE = TEST ZpusobyOchranyPozemku.ZpusobOchrany{0}.Kod ATTRIBUTE_IS_MISSING ""
    TEST_MODE = TEST
    FAILED -> ListExploder_5
ListExploder_5
    ATTR_ACCUM_MODE = Prefix List Attributes
    INCOMING_PREFIX = ZO
    INDEX_ATTR = _element_index
    LIST_ATTR = ZpusobyOchranyPozemku.ZpusobOchrany{}
    ELEMENTS -> AttributeKeeper_21
AttributeKeeper_21
    CREATE_BULK_MODE_FEATURES = NO
    KEEP_ATTRS = Id,ZORizeniId,ZOIdTransakce,ZOKod,ZOTypOchranyKod
    -> AttributeManager_15
AttributeManager_15
    ATTR_TABLE:
      SET_TO ZMENA_GRAFIKY = N
      SET_TO PUVOD = 1
      SET_TO ORIENTATION = 90
      RENAME_SET_VALUE Id > PARCELA_ID
      RENAME_SET_VALUE ZOKod > ZPUSOB_OCHRANY_KOD
      RENAME_SET_VALUE ZOIdTransakce > ID_TRANS_RUIAN
      RENAME_SET_VALUE ZORizeniId > RIZENI_ID
    -> TestFilter_33

Bookmark: POU - POVERENY OBECNI URAD
AttributeKeeper_11
    CREATE_BULK_MODE_FEATURES = NO
    KEEP_ATTRS = IdTransakce,Nespravny,PlatiDo,PlatiOd,GlobalniIdNavrhuZmeny,Kod,Nazev,SpravniObecKod,Orp.Kod
    -> DateTimeConverter_11
DateTimeConverter_11
    DATETIME_ATTR = PlatiDo PlatiOd
    IN_FORMAT = ISO
    OUT_FORMAT = FME
    PASSTHROUGH = YES
    REPAIR_INPUT = NO
    TEST_INPUT = 2013-12-05T00:00:00
    -> AttributeManager_10
AttributeManager_10
    ATTR_TABLE:
      SET_TO ZMENA_GRAFIKY = N
      SET_TO PUVOD = 1
      SET_TO PLATI_OD = @TimeZoneSet(@Value(PlatiOd),+01:00,auto)
      SET_TO ORIENTATION = 90
      SET_TO ID_TRANS_RUIAN = @Value(IdTransakce)
      SET_TO NZ_ID_GLOBALNI = @Value(GlobalniIdNavrhuZmeny)
      RENAME_SET_VALUE Kod > KOD
      RENAME_SET_VALUE Nespravny > NESPRAVNY = FME_CONDITIONAL:DEFAULT_VALUE'FME_NULL_VALUE'BOOL_OP;OR;COMPOSITE_TEST;1;TEST @Value(Nespravny) = true'1'FME_NUM_CONDITIONS2___
      REMOVE PlatiOd
      RENAME_SET_VALUE PlatiDo > PLATI_DO
      RENAME_SET_VALUE IdTransakce > ID_TRANS_RUIAN
      RENAME_SET_VALUE GlobalniIdNavrhuZmeny > NZ_ID_GLOBALNI
      RENAME_SET_VALUE Nazev > NAZEV
      RENAME_SET_VALUE SpravniObecKod > SPRAVNI_OBEC_KOD
      RENAME_SET_VALUE Orp.Kod > ORP_KOD
    -> GeometryFilter_11
GeometryFilter_11
    FILTER_MODE = SIMPLE
    FILTER_MULTI = FILTER_TYPES]"Point Area"]FME_CONTROLLER_QUERY_FILE]]FME_CONTROLLER_CHOICE]Simple
    Point -> GeometryRefiner_14
    Area -> GeometryRefiner_15
GeometryRefiner_14
    -> TestFilter_18
GeometryRefiner_15
    -> GeometryExtractor_6
GeometryExtractor_6
    ATTR = _geometry
    KIND_LONG = OGC Well Known Text
    OGCVERSION = 1.2
    OGC_WKT_PRECISION_DISPLAY = 64-bit
    REMOVE_GEOMETRY = No
    -> GeometryReplacer_6
GeometryReplacer_6
    KIND_LONG = OGC Well Known Text
    OGC_WKT_PRECISION_DISPLAY = 64-bit
    REMOVE_ATTRIBUTE = Yes
    SOURCE = @Value(_geometry)
    -> Aggregator_5
Aggregator_5
    ACCUM_ATTRS_NAME = Use Attributes From One Feature
    AGGREGATE_TYPE = Homogeneous Collection (If Possible)
    GROUP_BY = KOD
    MODE = Geometry - Assemble One Level
    SEP = ,
    AGGREGATE -> GeometryFilter_12
GeometryFilter_12
    FILTER_MODE = COMPLETE
    FILTER_MULTI = FILTER_TYPES]"Aggregate MultiArea"]INSTANCES]INSTANCE]FME_CONTROLLER_QUERY_FILE]]FME_CONTROLLER_CHOICE]Complete
    MultiArea -> TestFilter_19
    Aggregate -> GeometryRefiner_16
GeometryRefiner_16
    -> TestFilter_19

Bookmark: REGION SOUDRZNOSTI
AttributeKeeper_12
    CREATE_BULK_MODE_FEATURES = NO
    KEEP_ATTRS = IdTransakce,Nespravny,PlatiDo,PlatiOd,GlobalniIdNavrhuZmeny,Kod,Nazev,NutsLau,Stat.Kod
    -> DateTimeConverter_12
DateTimeConverter_12
    DATETIME_ATTR = PlatiDo PlatiOd
    IN_FORMAT = ISO
    OUT_FORMAT = FME
    PASSTHROUGH = YES
    REPAIR_INPUT = NO
    TEST_INPUT = 2013-12-05T00:00:00
    -> AttributeManager_11
AttributeManager_11
    ATTR_TABLE:
      SET_TO ZMENA_GRAFIKY = N
      SET_TO PUVOD = 1
      SET_TO PLATI_OD = @TimeZoneSet(@Value(PlatiOd),+01:00,auto)
      SET_TO ORIENTATION = 90
      SET_TO ID_TRANS_RUIAN = @Value(IdTransakce)
      SET_TO NZ_ID_GLOBALNI = @Value(GlobalniIdNavrhuZmeny)
      RENAME_SET_VALUE Kod > KOD
      RENAME_SET_VALUE Nespravny > NESPRAVNY = FME_CONDITIONAL:DEFAULT_VALUE'FME_NULL_VALUE'BOOL_OP;OR;COMPOSITE_TEST;1;TEST @Value(Nespravny) = true'1'FME_NUM_CONDITIONS2___
      REMOVE PlatiOd
      RENAME_SET_VALUE PlatiDo > PLATI_DO
      RENAME_SET_VALUE IdTransakce > ID_TRANS_RUIAN
      RENAME_SET_VALUE GlobalniIdNavrhuZmeny > NZ_ID_GLOBALNI
      RENAME_SET_VALUE Nazev > NAZEV
      RENAME_SET_VALUE Stat.Kod > STAT_KOD
      RENAME_SET_VALUE NutsLau > NUTS_LAU
    -> GeometryFilter_13
GeometryFilter_13
    FILTER_MODE = SIMPLE
    FILTER_MULTI = FILTER_TYPES]"Point Area"]FME_CONTROLLER_QUERY_FILE]]FME_CONTROLLER_CHOICE]Simple
    Point -> GeometryRefiner_17
    Area -> GeometryRefiner_18
GeometryRefiner_17
    -> TestFilter_20
GeometryRefiner_18
    -> GeometryExtractor_7
GeometryExtractor_7
    ATTR = _geometry
    KIND_LONG = OGC Well Known Text
    OGCVERSION = 1.2
    OGC_WKT_PRECISION_DISPLAY = 64-bit
    REMOVE_GEOMETRY = No
    -> GeometryReplacer_7
GeometryReplacer_7
    KIND_LONG = OGC Well Known Text
    OGC_WKT_PRECISION_DISPLAY = 64-bit
    REMOVE_ATTRIBUTE = Yes
    SOURCE = @Value(_geometry)
    -> Aggregator_6
Aggregator_6
    ACCUM_ATTRS_NAME = Use Attributes From One Feature
    AGGREGATE_TYPE = Homogeneous Collection (If Possible)
    GROUP_BY = KOD
    MODE = Geometry - Assemble One Level
    SEP = ,
    AGGREGATE -> GeometryFilter_14
GeometryFilter_14
    FILTER_MODE = COMPLETE
    FILTER_MULTI = FILTER_TYPES]"Aggregate MultiArea"]INSTANCES]INSTANCE]FME_CONTROLLER_QUERY_FILE]]FME_CONTROLLER_CHOICE]Complete
    MultiArea -> TestFilter_21
    Aggregate -> GeometryRefiner_19
GeometryRefiner_19
    -> TestFilter_21

Bookmark: SPRAVNI OBVOD
AttributeKeeper_17
    CREATE_BULK_MODE_FEATURES = NO
    KEEP_ATTRS = IdTransakce,Nespravny,PlatiDo,PlatiOd,GlobalniIdNavrhuZmeny,Kod,Nazev,Obec.Kod,Obec.Pou.Kod,SpravniMomcKod
    -> DateTimeConverter_17
DateTimeConverter_17
    DATETIME_ATTR = PlatiDo PlatiOd
    IN_FORMAT = ISO
    OUT_FORMAT = FME
    PASSTHROUGH = YES
    REPAIR_INPUT = NO
    TEST_INPUT = 2013-12-05T00:00:00
    -> AttributeManager_16
AttributeManager_16
    ATTR_TABLE:
      SET_TO ZMENA_GRAFIKY = N
      SET_TO PUVOD = 1
      SET_TO PLATI_OD = @TimeZoneSet(@Value(PlatiOd),+01:00,auto)
      SET_TO ORIENTATION = 90
      SET_TO ID_TRANS_RUIAN = @Value(IdTransakce)
      RENAME_SET_VALUE Nespravny > NESPRAVNY = FME_CONDITIONAL:DEFAULT_VALUE'FME_NULL_VALUE'BOOL_OP;OR;COMPOSITE_TEST;1;TEST @Value(Nespravny) = true'1'FME_NUM_CONDITIONS2___
      REMOVE PlatiOd
      RENAME_SET_VALUE PlatiDo > PLATI_DO
      RENAME_SET_VALUE IdTransakce > ID_TRANS_RUIAN
      RENAME_SET_VALUE Kod > KOD
      RENAME_SET_VALUE Nazev > NAZEV
      RENAME_SET_VALUE SpravniMomcKod > SPRAVNI_MOMC_KOD
      RENAME_SET_VALUE Obec.Kod > OBEC_KOD
      RENAME_SET_VALUE Obec.Pou.Kod > POU_KOD
      RENAME_SET_VALUE GlobalniIdNavrhuZmeny > NZ_ID_GLOBALNI
      SET_TO ZMENA_DETAILU = N
    -> GeometryFilter_22
GeometryFilter_22
    FILTER_MODE = SIMPLE
    FILTER_MULTI = FILTER_TYPES]"Point Area"]FME_CONTROLLER_QUERY_FILE]]FME_CONTROLLER_CHOICE]Simple
    Point -> GeometryRefiner_31
    Area -> GeometryRefiner_32
GeometryRefiner_31
    -> TestFilter_22
GeometryRefiner_32
    -> GeometryExtractor_11
GeometryExtractor_11
    ATTR = _geometry
    KIND_LONG = OGC Well Known Text
    OGCVERSION = 1.2
    OGC_WKT_PRECISION_DISPLAY = 64-bit
    REMOVE_GEOMETRY = No
    -> GeometryReplacer_11
GeometryReplacer_11
    KIND_LONG = OGC Well Known Text
    OGC_WKT_PRECISION_DISPLAY = 64-bit
    REMOVE_ATTRIBUTE = Yes
    SOURCE = @Value(_geometry)
    -> Aggregator_11
Aggregator_11
    ACCUM_ATTRS_NAME = Use Attributes From One Feature
    AGGREGATE_TYPE = Homogeneous Collection (If Possible)
    GROUP_BY = KOD
    MODE = Geometry - Assemble One Level
    SEP = ,
    AGGREGATE -> GeometryFilter_23
GeometryFilter_23
    FILTER_MODE = COMPLETE
    FILTER_MULTI = FILTER_TYPES]"Aggregate MultiArea"]INSTANCES]INSTANCE]FME_CONTROLLER_QUERY_FILE]]FME_CONTROLLER_CHOICE]Complete
    MultiArea -> TestFilter_23
    Aggregate -> GeometryRefiner_33
GeometryRefiner_33
    -> TestFilter_23

Bookmark: STAT
AttributeKeeper_13
    CREATE_BULK_MODE_FEATURES = NO
    KEEP_ATTRS = IdTransakce,Nespravny,PlatiDo,PlatiOd,GlobalniIdNavrhuZmeny,Kod,Nazev,NutsLau,Stat.Kod
    -> DateTimeConverter_13
DateTimeConverter_13
    DATETIME_ATTR = PlatiDo PlatiOd
    IN_FORMAT = ISO
    OUT_FORMAT = FME
    PASSTHROUGH = YES
    REPAIR_INPUT = NO
    TEST_INPUT = 2013-12-05T00:00:00
    -> AttributeManager_12
AttributeManager_12
    ATTR_TABLE:
      SET_TO ZMENA_GRAFIKY = N
      SET_TO PUVOD = 1
      SET_TO PLATI_OD = @TimeZoneSet(@Value(PlatiOd),+01:00,auto)
      SET_TO ORIENTATION = 90
      SET_TO ID_TRANS_RUIAN = @Value(IdTransakce)
      SET_TO NZ_ID_GLOBALNI = @Value(GlobalniIdNavrhuZmeny)
      RENAME_SET_VALUE Kod > KOD
      RENAME_SET_VALUE Nespravny > NESPRAVNY = FME_CONDITIONAL:DEFAULT_VALUE'FME_NULL_VALUE'BOOL_OP;OR;COMPOSITE_TEST;1;TEST @Value(Nespravny) = true'1'FME_NUM_CONDITIONS2___
      REMOVE PlatiOd
      RENAME_SET_VALUE PlatiDo > PLATI_DO
      RENAME_SET_VALUE IdTransakce > ID_TRANS_RUIAN
      RENAME_SET_VALUE GlobalniIdNavrhuZmeny > NZ_ID_GLOBALNI
      RENAME_SET_VALUE Nazev > NAZEV
      RENAME_SET_VALUE NutsLau > NUTS_LAU
    -> GeometryFilter_15
GeometryFilter_15
    FILTER_MODE = SIMPLE
    FILTER_MULTI = FILTER_TYPES]"Point Area"]FME_CONTROLLER_QUERY_FILE]]FME_CONTROLLER_CHOICE]Simple
    Point -> GeometryRefiner_20
    Area -> GeometryRefiner_21
GeometryRefiner_20
    -> TestFilter_24
GeometryRefiner_21
    -> Aggregator_8
Aggregator_8
    ACCUM_ATTRS_NAME = Use Attributes From One Feature
    AGGREGATE_TYPE = Homogeneous Collection (If Possible)
    GROUP_BY = KOD
    MODE = Geometry - Assemble One Level
    SEP = ,
    AGGREGATE -> TestFilter_25

Bookmark: STAVEBNI OBJEKT
AttributeKeeper_6
    CREATE_BULK_MODE_FEATURES = NO
    KEEP_ATTRS = IdTransakce,Nespravny,PlatiDo,PlatiOd,Dokonceni,DruhKonstrukceKod,GlobalniIdNavrhuZmeny,Kod,ObestavenyProstor,PocetBytu,PocetPodlazi,PodlahovaPlocha,PripojeniKanalizaceKod,PripojeniPlynKod,PripojeniVodovodKod,TypStavebnihoObjektuKod,VybaveniVytahemKod,ZastavenaPlocha,ZpusobVytapeniKod,ZpusobVyuzitiKod,CastObce.Kod,IdentifikacniParcela.Id,IsknBudovaId,Momc.Kod
    -> DateTimeConverter_6
DateTimeConverter_6
    DATETIME_ATTR = PlatiDo PlatiOd Dokonceni
    IN_FORMAT = ISO
    OUT_FORMAT = FME
    PASSTHROUGH = YES
    REPAIR_INPUT = NO
    TEST_INPUT = 2013-12-05T00:00:00
    -> AttributeManager_17
AttributeManager_17
    ATTR_TABLE:
      SET_TO ZMENA_GRAFIKY = N
      SET_TO PUVOD = 1
      SET_TO PLATI_OD = @TimeZoneSet(@Value(PlatiOd),+01:00,auto)
      SET_TO ORIENTATION = 90
      SET_TO ID_TRANS_RUIAN = @Value(IdTransakce)
      RENAME_SET_VALUE Nespravny > NESPRAVNY = FME_CONDITIONAL:DEFAULT_VALUE'FME_NULL_VALUE'BOOL_OP;OR;COMPOSITE_TEST;1;TEST @Value(Nespravny) = true'1'FME_NUM_CONDITIONS2___
      REMOVE PlatiOd
      RENAME_SET_VALUE PlatiDo > PLATI_DO
      RENAME_SET_VALUE IdTransakce > ID_TRANS_RUIAN
      RENAME_SET_VALUE Kod > KOD
      RENAME_SET_VALUE GlobalniIdNavrhuZmeny > NZ_ID_GLOBALNI
      RENAME_SET_VALUE IdentifikacniParcela.Id > IDENTIFIKACNI_PARCELA_ID
      RENAME_SET_VALUE TypStavebnihoObjektuKod > TYP_KOD
      RENAME_SET_VALUE ZpusobVyuzitiKod > ZPUSOB_VYUZITI_KOD
      RENAME_SET_VALUE CastObce.Kod > COBCE_KOD
      RENAME_SET_VALUE Momc.Kod > MOMC_KOD
      RENAME_SET_VALUE IsknBudovaId > BUDOVA_ID
      RENAME_SET_VALUE Dokonceni > DOKONCENI = FME_CONDITIONAL:DEFAULT_VALUE'@TimeZoneSet(@Value(DOKONCENI),+01:00,auto)'BOOL_OP;OR;COMPOSITE_TEST;1 OR 2 OR 3;TEST Dokonceni ATTRIBUTE_VALUE_NULL _FME_BLANK_STRING_;TEST Dokonceni ATTRIBUTE_IS_MISSING _FME_BLANK_STRING_;TEST Dokonceni ATTRIBUTE_IS_EMPTY _FME_BLANK_STRING_'FME_NULL_VALUE'FME_NUM_CONDITIONS2___
      RENAME_SET_VALUE DruhKonstrukceKod > DRUH_KONSTRUKCE_KOD
      RENAME_SET_VALUE ObestavenyProstor > OBESTAVENY_PROSTOR
      RENAME_SET_VALUE PocetBytu > POCET_BYTU
      RENAME_SET_VALUE PocetPodlazi > POCET_PODLAZI
      RENAME_SET_VALUE PodlahovaPlocha > PODLAHOVA_PLOCHA
      RENAME_SET_VALUE PripojeniKanalizaceKod > PRIPOJ_KANAL_SIT_KOD
      RENAME_SET_VALUE PripojeniPlynKod > PRIPOJ_PLYN_KOD
      RENAME_SET_VALUE PripojeniVodovodKod > PRIPOJ_VODOVOD_KOD
      RENAME_SET_VALUE VybaveniVytahemKod > JE_VYTAH_KOD
      RENAME_SET_VALUE ZastavenaPlocha > ZASTAVENA_PLOCHA
      RENAME_SET_VALUE ZpusobVytapeniKod > ZPUSOB_VYTAPENI_KOD
    USER_EXPOSED_ATTRIBUTES = Nazev,Obec.Pou.Kod
    -> GeometryFilter_4
GeometryFilter_4
    FILTER_MODE = SIMPLE
    FILTER_MULTI = FILTER_TYPES]"Point Area"]FME_CONTROLLER_QUERY_FILE]]FME_CONTROLLER_CHOICE]Simple
    Point -> GeometryRefiner_5
    Area -> GeometryRefiner_6
    <UNFILTERED> -> TestFilter_26
    <UNFILTERED> -> TestFilter_27
GeometryRefiner_5
    -> TestFilter_26
GeometryRefiner_6
    -> GeometryExtractor_2
GeometryExtractor_2
    ATTR = _geometry
    KIND_LONG = OGC Well Known Text
    OGCVERSION = 1.2
    OGC_WKT_PRECISION_DISPLAY = 64-bit
    REMOVE_GEOMETRY = No
    -> GeometryReplacer_2
GeometryReplacer_2
    KIND_LONG = OGC Well Known Text
    OGC_WKT_PRECISION_DISPLAY = 64-bit
    REMOVE_ATTRIBUTE = Yes
    SOURCE = @Value(_geometry)
    -> GeometryFilter_25
GeometryFilter_25
    FILTER_MODE = COMPLETE
    FILTER_MULTI = FILTER_TYPES]"Donut Polygon MultiArea"]INSTANCES]INSTANCE]FME_CONTROLLER_QUERY_FILE]]FME_CONTROLLER_CHOICE]Complete
    Polygon -> Aggregator
    Donut -> Aggregator
    MultiArea -> TestFilter_27
Aggregator
    ACCUM_ATTRS_NAME = Use Attributes From One Feature
    AGGREGATE_TYPE = Homogeneous Collection (If Possible)
    GROUP_BY = KOD
    MODE = Geometry - Assemble One Level
    SEP = ,
    AGGREGATE -> TestFilter_27

Bookmark: Detailní TEA (technicko-ekonomické atributy)
Tester_4
    BOOL_OP = OR
    TEST_CLAUSE = TEST DetailniTEA.DetailniTEA{0}.Kod ATTRIBUTE_IS_MISSING ""
    TEST_MODE = TEST
    FAILED -> ListExploder_3
ListExploder_3
    ATTR_ACCUM_MODE = Prefix List Attributes
    INCOMING_PREFIX = TEA
    INDEX_ATTR = _element_index
    LIST_ATTR = DetailniTEA.DetailniTEA{}
    ELEMENTS -> AttributeKeeper_19
AttributeKeeper_19
    CREATE_BULK_MODE_FEATURES = NO
    KEEP_ATTRS = TEAAdresniMistoKod.Kod{0},TEADruhKonstrukceKod,TEAGlobalniIdNavrhuZmeny,TEAKod,TEANespravny,TEAPlatiOd,TEAPocetBytu,TEAPocetPodlazi,TEAPripojeniKanalizaceKod,TEAPripojeniPlynKod,TEAPripojeniVodovodKod,TEAZpusobVytapeniKod,Kod
    -> DateTimeConverter_18
DateTimeConverter_18
    DATETIME_ATTR = TEAPlatiOd
    IN_FORMAT = ISO
    OUT_FORMAT = FME
    PASSTHROUGH = YES
    REPAIR_INPUT = NO
    TEST_INPUT = 2013-12-05T00:00:00
    -> AttributeManager_18
AttributeManager_18
    ATTR_TABLE:
      SET_TO ZMENA_GRAFIKY = N
      SET_TO PUVOD = 1
      SET_TO ORIENTATION = 90
      RENAME_SET_VALUE Kod > STAVOBJ_KOD
      RENAME_SET_VALUE TEAKod > KOD
      RENAME_SET_VALUE TEAPlatiOd > PLATI_OD = @TimeZoneSet(@Value(PLATI_OD),+01:00,auto)
      RENAME_SET_VALUE TEANespravny > NESPRAVNY = FME_CONDITIONAL:DEFAULT_VALUE'FME_NULL_VALUE'BOOL_OP;OR;COMPOSITE_TEST;1;TEST @Value(NESPRAVNY) = true'1'FME_NUM_CONDITIONS2___
      RENAME_SET_VALUE TEAGlobalniIdNavrhuZmeny > NZ_ID_GLOBALNI
      RENAME_SET_VALUE TEADruhKonstrukceKod > DRUH_KONSTRUKCE_KOD
      RENAME_SET_VALUE TEAPocetBytu > POCET_BYTU
      RENAME_SET_VALUE TEAPocetPodlazi > POCET_PODLAZI
      RENAME_SET_VALUE TEAPripojeniKanalizaceKod > PRIPOJ_KANAL_SIT_KOD
      RENAME_SET_VALUE TEAPripojeniPlynKod > PRIPOJ_PLYN_KOD
      RENAME_SET_VALUE TEAPripojeniVodovodKod > PRIPOJ_VODOVOD_KOD
      RENAME_SET_VALUE TEAZpusobVytapeniKod > ZPUSOB_VYTAPENI_KOD
      REMOVE TEAAdresniMistoKod.Kod{}
    USER_EXPOSED_ATTRIBUTES = Nazev,Obec.Pou.Kod
    -> TestFilter_34

Bookmark: ULICE
AttributeKeeper_7
    CREATE_BULK_MODE_FEATURES = NO
    KEEP_ATTRS = GlobalniIdNavrhuZmeny,IdTransakce,Kod,Nespravny,PlatiDo,PlatiOd,Obec.Kod,Nazev
    -> DateTimeConverter_7
DateTimeConverter_7
    DATETIME_ATTR = PlatiDo PlatiOd
    IN_FORMAT = ISO
    OUT_FORMAT = FME
    PASSTHROUGH = YES
    REPAIR_INPUT = NO
    TEST_INPUT = 2013-12-05T00:00:00
    -> AttributeManager_20
AttributeManager_20
    ATTR_TABLE:
      SET_TO ZMENA_GRAFIKY = N
      SET_TO PUVOD = 1
      SET_TO PLATI_OD = @TimeZoneSet(@Value(PlatiOd),+01:00,auto)
      SET_TO ORIENTATION = 90
      SET_TO ID_TRANS_RUIAN = @Value(IdTransakce)
      RENAME_SET_VALUE Nespravny > NESPRAVNY = FME_CONDITIONAL:DEFAULT_VALUE'FME_NULL_VALUE'BOOL_OP;OR;COMPOSITE_TEST;1;TEST @Value(Nespravny) = true'1'FME_NUM_CONDITIONS2___
      REMOVE PlatiOd
      RENAME_SET_VALUE PlatiDo > PLATI_DO
      RENAME_SET_VALUE IdTransakce > ID_TRANS_RUIAN
      RENAME_SET_VALUE Kod > KOD
      RENAME_SET_VALUE Nazev > NAZEV
      RENAME_SET_VALUE Obec.Kod > OBEC_KOD
      RENAME_SET_VALUE GlobalniIdNavrhuZmeny > NZ_ID_GLOBALNI
      SET_TO ZMENA_DETAILU = N
    -> GeometryFilter_5
GeometryFilter_5
    FILTER_MODE = SIMPLE
    FILTER_MULTI = FILTER_TYPES]"Point Line"]FME_CONTROLLER_QUERY_FILE]]FME_CONTROLLER_CHOICE]Simple
    Curve -> TestFilter_36
    <UNFILTERED> -> TestFilter_36

Bookmark: VUSC - Vyšší územně samosprávný celek
AttributeKeeper_14
    CREATE_BULK_MODE_FEATURES = NO
    KEEP_ATTRS = IdTransakce,Nespravny,PlatiDo,PlatiOd,GlobalniIdNavrhuZmeny,Kod,Nazev,NutsLau,RegionSoudrznosti.Kod
    -> DateTimeConverter_14
DateTimeConverter_14
    DATETIME_ATTR = PlatiDo PlatiOd
    IN_FORMAT = ISO
    OUT_FORMAT = FME
    PASSTHROUGH = YES
    REPAIR_INPUT = NO
    TEST_INPUT = 2013-12-05T00:00:00
    -> AttributeManager_13
AttributeManager_13
    ATTR_TABLE:
      SET_TO ZMENA_GRAFIKY = N
      SET_TO PUVOD = 1
      SET_TO PLATI_OD = @TimeZoneSet(@Value(PlatiOd),+01:00,auto)
      SET_TO ORIENTATION = 90
      SET_TO ID_TRANS_RUIAN = @Value(IdTransakce)
      SET_TO NZ_ID_GLOBALNI = @Value(GlobalniIdNavrhuZmeny)
      RENAME_SET_VALUE Kod > KOD
      RENAME_SET_VALUE Nespravny > NESPRAVNY = FME_CONDITIONAL:DEFAULT_VALUE'FME_NULL_VALUE'BOOL_OP;OR;COMPOSITE_TEST;1;TEST @Value(Nespravny) = true'1'FME_NUM_CONDITIONS2___
      REMOVE PlatiOd
      RENAME_SET_VALUE PlatiDo > PLATI_DO
      RENAME_SET_VALUE IdTransakce > ID_TRANS_RUIAN
      RENAME_SET_VALUE GlobalniIdNavrhuZmeny > NZ_ID_GLOBALNI
      RENAME_SET_VALUE Nazev > NAZEV
      RENAME_SET_VALUE NutsLau > NUTS_LAU
      RENAME_SET_VALUE RegionSoudrznosti.Kod > REGSOUDR_KOD
    -> GeometryFilter_16
GeometryFilter_16
    FILTER_MODE = SIMPLE
    FILTER_MULTI = FILTER_TYPES]"Point Area"]FME_CONTROLLER_QUERY_FILE]]FME_CONTROLLER_CHOICE]Simple
    Point -> GeometryRefiner_22
    Area -> GeometryRefiner_23
GeometryRefiner_22
    -> TestFilter_28
GeometryRefiner_23
    -> GeometryExtractor_8
GeometryExtractor_8
    ATTR = _geometry
    KIND_LONG = OGC Well Known Text
    OGCVERSION = 1.2
    OGC_WKT_PRECISION_DISPLAY = 64-bit
    REMOVE_GEOMETRY = No
    -> GeometryReplacer_8
GeometryReplacer_8
    KIND_LONG = OGC Well Known Text
    OGC_WKT_PRECISION_DISPLAY = 64-bit
    REMOVE_ATTRIBUTE = Yes
    SOURCE = @Value(_geometry)
    -> Aggregator_7
Aggregator_7
    ACCUM_ATTRS_NAME = Use Attributes From One Feature
    AGGREGATE_TYPE = Homogeneous Collection (If Possible)
    GROUP_BY = KOD
    MODE = Geometry - Assemble One Level
    SEP = ,
    AGGREGATE -> GeometryFilter_17
GeometryFilter_17
    FILTER_MODE = COMPLETE
    FILTER_MULTI = FILTER_TYPES]"Aggregate MultiArea"]INSTANCES]INSTANCE]FME_CONTROLLER_QUERY_FILE]]FME_CONTROLLER_CHOICE]Complete
    MultiArea -> TestFilter_29
    Aggregate -> GeometryRefiner_24
GeometryRefiner_24
    -> TestFilter_29

Bookmark: ZSJ - ZAKLADNI SIDELNI JEDNOTKA
AttributeKeeper_8
    CREATE_BULK_MODE_FEATURES = NO
    KEEP_ATTRS = IdTransakce,Nespravny,PlatiDo,PlatiOd,KatastralniUzemi.Kod,CharakterZsjKod,Kod,MluvnickeCharakteristiky.Pad2,MluvnickeCharakteristiky.Pad3,MluvnickeCharakteristiky.Pad4,MluvnickeCharakteristiky.Pad5,MluvnickeCharakteristiky.Pad6,MluvnickeCharakteristiky.Pad7,Nazev,Vymera,GlobalniIdNavrhuZmeny
    -> DateTimeConverter_8
DateTimeConverter_8
    DATETIME_ATTR = PlatiDo PlatiOd
    IN_FORMAT = ISO
    OUT_FORMAT = FME
    PASSTHROUGH = YES
    REPAIR_INPUT = NO
    TEST_INPUT = 2013-12-05T00:00:00
    -> AttributeManager_21
AttributeManager_21
    ATTR_TABLE:
      SET_TO ZMENA_GRAFIKY = N
      SET_TO PUVOD = 1
      SET_TO PLATI_OD = @TimeZoneSet(@Value(PlatiOd),+01:00,auto)
      SET_TO ORIENTATION = 90
      SET_TO ID_TRANS_RUIAN = @Value(IdTransakce)
      RENAME_SET_VALUE Nespravny > NESPRAVNY = FME_CONDITIONAL:DEFAULT_VALUE'FME_NULL_VALUE'BOOL_OP;OR;COMPOSITE_TEST;1;TEST @Value(Nespravny) = true'1'FME_NUM_CONDITIONS2___
      REMOVE PlatiOd
      RENAME_SET_VALUE PlatiDo > PLATI_DO
      RENAME_SET_VALUE IdTransakce > ID_TRANS_RUIAN
      RENAME_SET_VALUE Kod > KOD
      RENAME_SET_VALUE Nazev > NAZEV
      RENAME_SET_VALUE GlobalniIdNavrhuZmeny > NZ_ID_GLOBALNI
      SET_TO ZMENA_DETAILU = N
      RENAME_SET_VALUE KatastralniUzemi.Kod > KATUZ_KOD
      RENAME_SET_VALUE MluvnickeCharakteristiky.Pad2 > MLUV_CHAR_PAD_2
      RENAME_SET_VALUE MluvnickeCharakteristiky.Pad3 > MLUV_CHAR_PAD_3
      RENAME_SET_VALUE MluvnickeCharakteristiky.Pad4 > MLUV_CHAR_PAD_4
      RENAME_SET_VALUE MluvnickeCharakteristiky.Pad5 > MLUV_CHAR_PAD_5
      RENAME_SET_VALUE MluvnickeCharakteristiky.Pad6 > MLUV_CHAR_PAD_6
      RENAME_SET_VALUE MluvnickeCharakteristiky.Pad7 > MLUV_CHAR_PAD_7
      RENAME_SET_VALUE Vymera > VYMERA
      RENAME_SET_VALUE CharakterZsjKod > CHARAKTER_ZSJ_KOD
    USER_EXPOSED_ATTRIBUTES = Obec.Kod
    -> GeometryFilter_6
GeometryFilter_6
    FILTER_MODE = SIMPLE
    FILTER_MULTI = FILTER_TYPES]"Point Area"]FME_CONTROLLER_QUERY_FILE]]FME_CONTROLLER_CHOICE]Simple
    Point -> GeometryRefiner_7
    Area -> GeometryRefiner_8
GeometryRefiner_7
    -> TestFilter_30
GeometryRefiner_8
    -> GeometryExtractor_3
GeometryExtractor_3
    ATTR = _geometry
    KIND_LONG = OGC Well Known Text
    OGCVERSION = 1.2
    OGC_WKT_PRECISION_DISPLAY = 64-bit
    REMOVE_GEOMETRY = No
    -> GeometryReplacer_3
GeometryReplacer_3
    KIND_LONG = OGC Well Known Text
    OGC_WKT_PRECISION_DISPLAY = 64-bit
    REMOVE_ATTRIBUTE = Yes
    SOURCE = @Value(_geometry)
    -> Aggregator_2
Aggregator_2
    ACCUM_ATTRS_NAME = Use Attributes From One Feature
    AGGREGATE_TYPE = Homogeneous Collection (If Possible)
    GROUP_BY = KOD
    MODE = Geometry - Assemble One Level
    SEP = ,
    AGGREGATE -> TestFilter_31

Bookmark: Způsob ochrany stavebního objektu
Tester_5
    BOOL_OP = OR
    TEST_CLAUSE = TEST ZpusobyOchrany.ZpusobOchrany{0}.Kod ATTRIBUTE_IS_MISSING ""
    TEST_MODE = TEST
    FAILED -> ListExploder_4
ListExploder_4
    ATTR_ACCUM_MODE = Prefix List Attributes
    INCOMING_PREFIX = ZO
    INDEX_ATTR = _element_index
    LIST_ATTR = ZpusobyOchrany.ZpusobOchrany{}
    ELEMENTS -> AttributeKeeper_20
AttributeKeeper_20
    CREATE_BULK_MODE_FEATURES = NO
    KEEP_ATTRS = ZOIdTransakce,ZOKod,ZORizeniId,ZOTypOchranyKod,Kod
    -> AttributeManager_19
AttributeManager_19
    ATTR_TABLE:
      SET_TO ZMENA_GRAFIKY = N
      SET_TO PUVOD = 1
      SET_TO ORIENTATION = 90
      RENAME_SET_VALUE Kod > STAVOBJ_KOD
      RENAME_SET_VALUE ZOIdTransakce > ID_TRANS_RUIAN
      RENAME_SET_VALUE ZOKod > ZPUSOB_OCHRANY_KOD
      RENAME_SET_VALUE ZORizeniId > RIZENI_ID
    USER_EXPOSED_ATTRIBUTES = Nazev,Obec.Pou.Kod
    -> TestFilter_35
