FME workspace Maly_Seznam_to_Pruvodka_T.fmw

Parameters:
- KPJM = zdeborjan   # Zadajte KPJM
- Slozka = ETU_0806_JMA   # Slozka se souborem
- API_PARAM_P_T = https://restapidv2test.cezdata.corp/esb/ecm/document/v1/get-property-values/   # Produkce/Test
- Pevna_cesta = \\dfs03.cezdata.corp\CEZ\DKE\9050060_ŘTKE\TPKE\RIZEK\JMA do DOCMAN\Testovací dávky ICC
- FME_JOB_ID = 1   # FME Server Job ID

TestFilter_2
    DEFAULT_VALUE = Data
    PASSED_TEST_GROUP_OUTPUT = FIRST
    TEST_LIST = "BOOL_OP,OR,COMPOSITE_TEST,""""""1"""""",TEST_CLAUSE,TEST @Value(xlsx_row_id) = 3",Hlavička
    Hlavička -> Test_ciselniku_Company_Issuing_2 [REQUESTOR]
    Data -> FeatureJoiner_2 [LEFT]
Test_ciselniku_Company_Issuing_2: FeatureMerger
    ATTR_ACCUM_MODE = Merge Supplier
    ATTR_CONFLICT_RES = Use Requestor
    IGNORE_NULLS = No
    JOIN_KEYS = @Value(P) @Value(value) AUTO
    MERGE_TYPE = Attributes Only
    PROCESS_DUPS = NO
    REJECT_NULL_MISSING_KEYS = No
    SUPPLIERS_FIRST = No
    MERGED -> AttributeCreator_2
    UNMERGED_REQUESTOR -> Junction_5
    UNMERGED_REQUESTOR -> AttributeManager_7
AttributeCreator_2
    ATTR_TABLE = SET_TO Hlavicka v ciselniku = ANO
    -> Junction_5
Junction_5
    -> FeatureJoiner_2 [RIGHT]
    -> Tester_3
FeatureJoiner_2
    ATTR_CONFLICT_RES = Prefer Left
    GEOMETRY_HANDLING = Prefer Left
    JOIN_KEYS = Merging att Merging att AUTO
    JOIN_MODE = Left
    JOINED -> Tester_3
Tester_3
    BOOL_OP = OR
    TEST_CLAUSE = TEST @Value(Hlavicka v ciselniku) = ANO
    TEST_MODE = TEST
    PASSED -> AttributeRemover_2
AttributeRemover_2
    REMOVE_ATTRS = description,domainName,Hlavicka v ciselniku,value
    -> TestFilter_3
Note: Pozor na Test vs Produkce přepínač
Note: Test hlavičky
TestFilter_3
    DEFAULT_VALUE = Data
    TEST_LIST:
      "BOOL_OP,OR,COMPOSITE_TEST,""""""1 OR 2"""""",TEST_CLAUSE,TEST @Value(xlsx_row_id) = 1
      TEST @Value(xlsx_row_id) = 2",Atributy hlavičky,"BOOL_OP,OR,COMPOSITE_TEST,""""""<Unused>"""""",TEST_CLAUSE,TEST @Value(xlsx_row_id) = 3",Data hlavičky,"BOOL_OP,OR,COMPOSITE_TEST,""""""1"""""",TEST_CLAUSE,TEST @Value(xlsx_row_id) = 5",Atributy dat,"BOOL_OP,OR,COMPOSITE_TEST,""""""1 OR 2 OR 3"""""",TEST_CLAUSE,TEST @Value(xlsx_row_id) = 4
      TEST @Value(xlsx_row_id) = 6
      TEST xlsx_row_id NOT_ATTRIBUTE_HAS_A_VALUE """,Prázdné řádky
    Data hlavičky -> Sampler
    Data hlavičky -> JMA
    Data -> ABC_na_nazvy_v_Seznamu
ABC_na_nazvy_v_Seznamu: AttributeRenamer
    ATTR_TABLE:
      RENAME_SET_DEFAULT A > Poradove cislo
      RENAME_SET_DEFAULT B > Cislo SO
      RENAME_SET_DEFAULT C > Oznaceni PS_DPS
      RENAME_SET_DEFAULT D > Typ dokumentu
      RENAME_SET_DEFAULT E > Podtyp dokumentu
      RENAME_SET_DEFAULT F > DCC A1
      RENAME_SET_DEFAULT G > Nazev dokumentu
      RENAME_SET_DEFAULT H > Doplnujici nazev predmetu_umisteni
      RENAME_SET_DEFAULT I > Projekcni oznaceni KKS
      RENAME_SET_DEFAULT J > Archivacni cislo dokumentu
      RENAME_SET_DEFAULT K > Pocet listu v dokumentu
      RENAME_SET_DEFAULT L > Revize dokumentu
      RENAME_SET_DEFAULT N > Cesta elektronickeho souboru
      RENAME_SET_DEFAULT P > Datum vytvoreni
      RENAME_SET_DEFAULT xlsx_row_id > Cislo radku
      RENAME_SET_DEFAULT Q > Podslozka FileNetPath
    MISSING_INPUT_ATTRS = REMOVE
    -> FeatureMerger [REQUESTOR]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> FeatureMerger_2 [REQUESTOR]
    USED_SUPPLIER -> AttributeManager_3
Note: AttributeKeeper_9 : Output
Junction_14
    -> Sorter
Note: ERROR TABLE / 0000 0001 (1) - Duplicitni soubory po sloučení složek
StringReplacer
    CASE = NO
    FIND_TEXT = /
    NO_MATCH = _FME_NO_OP_
    REGEXP = NO
    REPLACE_TEXT = \
    SRC_ATTRS = FileNetPath,PathToFiles
    -> FeatureWriter [Output]
AttributeManager_7
    ATTR_TABLE:
      RENAME_SET_VALUE Cesta k Seznamu > Cesta elektronickeho souboru
      RENAME_SET_VALUE Název Seznamu > FileName
      RENAME_SET_VALUE xlsx_row_id > Cislo radku
      SET_TO Atribut = Zhotovitel
      SET_TO Hodnota atributu = @Value(P)
      SET_TO Popis chyby = Zadaný zhotovitel není v číselníku
      SET_TO Sheet_name = Chyby v Seznamu dokumentace
    -> AttributeKeeper_5
AttributeKeeper_5
    CREATE_BULK_MODE_FEATURES = NO
    KEEP_ATTRS = Atribut,Cesta elektronickeho souboru,FileName,Hodnota atributu,Popis chyby,Cislo radku,Sheet_name
    -> Sorter
Note: AttributeKeeper_4 : Output
Junction_3
    -> Sorter
Note: Popis_upozorneni_2 : Output
Junction_11
    -> Sorter
Sorter
    SORT_PARM = Cislo radku NATURAL ASCENDING
    SORTED -> FeatureWriter_2 [Sorted]

Bookmark: Číselník Docman - RestAPI
Creator_2
    GEOMTYPE = Geometry Object
    NUM = 1
    CREATED -> HTTPCaller
HTTPCaller
    ADDITIONAL_URL_PARAMETERS = DomainName;%
    AUTH_METHOD = Basic
    AUTH_PASSWORD =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
    AUTH_USERNAME = qpfmeserver
    CONNECTION_TIMEOUT_LENGTH = 60
    CUSTOM_HEADERS = messageId;$(FME_JOB_ID) timestamp;@DateTimeNow() sourceSystem;FME Server
    ERROR_ATTR = _error
    FOLLOW_REDIRECTS = FOLLOW_WITH_GET
    HTTP_METHOD = GET
    MAX_HTTP_VERSION = HTTP_1_1
    MAX_TRANSFERS_IN_PROGRESS = 10
    MINIMUM_ENCRYPTION_LEVEL = OS_DEFAULT
    MULTIPART_RESPONSE_HEADER_LIST_ATTR = _multipart_headers
    REDIRECT_AUTH = ORIGINAL_DOMAIN_ONLY
    RESPONSE_TYPE = Attribute
    SPLIT_MULTIPART_DOWNLOADS = YES
    TARGET_ATTR = _response_body
    TARGET_ATTR_ENCODING = fme-system
    TARGET_URL = $(API_PARAM_P_T)
    TRANSFER_TIMEOUT_LENGTH = 90
    USE_COOKIES = No
    VERIFY_SSL_CERTIFICATES = No
    -> AttributeCreator_4
AttributeCreator_4
    ATTR_TABLE = SET_TO _response_body = {"features":@Value(_response_body)}
    -> JSONFragmenter_2
JSONFragmenter_2
    EXPLODE_FORMAT = JSON
    EXTRACT_ATTR = Yes
    JSON_ATTR = _response_body
    JSON_QUERY = json["features"][*]
    READ_FROM_FILE = NO
    RECURSIVE = Yes
    REJECT_EMPTY_LISTS = YES
    FRAGMENTS -> AttributeExposer_3
AttributeExposer_3
    ATTR_LIST = value,domainName,description
    -> AttributeKeeper_7
AttributeKeeper_7
    CREATE_BULK_MODE_FEATURES = NO
    KEEP_ATTRS = description,domainName,value
    -> TestFilter_5
TestFilter_5
    DEFAULT_VALUE = <UNFILTERED>
    PASSED_TEST_GROUP_OUTPUT = FIRST
    TEST_LIST = "BOOL_OP,OR,COMPOSITE_TEST,""""""1"""""",TEST_CLAUSE,TEST @Value(domainName) = CompanyIssuing",CompanyIssuing,"BOOL_OP,OR,COMPOSITE_TEST,""""""1"""""",TEST_CLAUSE,TEST @Value(domainName) = DocumentSubType",DocumentSubType,"BOOL_OP,OR,COMPOSITE_TEST,""""""1"""""",TEST_CLAUSE,TEST @Value(domainName) = DocumentType",DocumentType,"BOOL_OP,OR,COMPOSITE_TEST,""""""1"""""",TEST_CLAUSE,TEST @Value(domainName) = SegmentationaccordingtoCSNEN6135A1",SegmentationaccordingtoCSNEN6135A1,"BOOL_OP,OR,COMPOSITE_TEST,""""""1"""""",TEST_CLAUSE,TEST @Value(domainName) = SegmentationaccordingtoCSNEN6135A3",SegmentationaccordingtoCSNEN6135A3
    CompanyIssuing -> Test_ciselniku_Company_Issuing_2 [SUPPLIER]
    DocumentSubType -> Test_ciselniku_Doc_SubType [SUPPLIER]
    DocumentType -> Test_ciselniku_Doc_Type [SUPPLIER]
    SegmentationaccordingtoCSNEN6135A1 -> Test_ciselniku_DCC_A1 [SUPPLIER]
    SegmentationaccordingtoCSNEN6135A3 -> Test_ciselniku_DCC_A2A3_2 [SUPPLIER]

Bookmark: Načtení dat
Creator
    GEOMTYPE = Geometry Object
    NUM = 1
    CREATED -> FeatureReader_2 [INITIATOR]
Note: Vylistuje soubor "Seznam dokumentace*.xlsm" v kombinaci pevně dané cesty a uživatelsky dodaném názvu složky
FeatureReader_2
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    COMBINE_GEOM = Use Result
    DATASET = $(Pevna_cesta)\$(Slozka)
    FORMAT = PATH
    OUTPUT_FEATURES_DISPLAY = Schema and Data Features
    PATH_GLOB_PATTERN = Seznam dokumentace*.xlsm
    PATH_NO_EMPTY_PROPERTIES = YES
    PATH_OFFSET_DATETIME = yes
    PATH_RECURSE_DIRECTORIES = NO
    PATH_RETRIEVE_FILE_PROPERTIES = YES
    PATH_TYPE = FILE
    PATH_USE_NON_STRING_ATTR = yes
    PATH -> AttributeManager_6
AttributeManager_6
    ATTR_TABLE:
      RENAME_SET_VALUE path_windows > Cesta k Seznamu
      RENAME_SET_VALUE path_directory_windows > Cesta ke slozce Seznamu
      RENAME_SET_VALUE path_rootname > Název Seznamu bez prip
      RENAME_SET_VALUE path_filename > Název Seznamu
      REMOVE path_unix
      REMOVE path_extension
      REMOVE path_filesize
      REMOVE path_ownername
      REMOVE path_readonly
      REMOVE path_modified_date
      REMOVE path_created_date
      REMOVE path_accessed_date
      REMOVE path_directory_unix
      REMOVE path_type
      REMOVE fme_geometry{0}
      REMOVE fme_geometry{}
    -> FeatureReader_3 [INITIATOR]
    -> FeatureReader_4 [INITIATOR]
Note: Načte Data z excelu
FeatureReader_3
    ATTR_ACCUM_MODE = Merge Initiator and Result
    ATTR_CONFLICT_RES = Use Result
    ATTR_IGNORE_NULLS = No
    COMBINE_GEOM = Use Result
    DATASET = @Value(Cesta k Seznamu)
    FORMAT = XLSXR
    INTERACT = NONE
    OUTPUT_FEATURES_DISPLAY = Data Features
    XLSXR_ALLOW_DOLLAR_SIGNS = YES
    XLSXR_APPLY_FILTERS = No
    XLSXR_CASE_SENSITIVE_FEATURE_TYPES = YES
    XLSXR_CREATE_FEATURE_TABLES_FROM_DATA = Yes
    XLSXR_EXCEL_COL_NAMES = YES
    XLSXR_EXPAND_MERGED_CELLS = Yes
    XLSXR_FORCE_DATETIME = NO
    XLSXR_QUERY_FEATURE_TYPES_FOR_MERGE_FILTERS = Yes
    XLSXR_READ_BLANK_AS = Missing
    XLSXR_READ_FORM_CONTROLS = NONE
    XLSXR_READ_RASTER_MODE = None
    XLSXR_REPLACE_ONLY_NEWLINES_CARRIAGE_RETURNS = YES
    XLSXR_SCAN_MAX_FEATURES = 1000
    XLSXR_SCHEMA_HANDLING_REVISION = 2
    XLSXR_SKIP_EMPTY_ROWS = YES
    XLSXR_STRIP_SHEETNAME_SPACES = YES
    XLSXR_TRIM_ATTR_NAME_WHITESPACE = Yes
    XLSXR_USE_CUSTOM_SCHEMA = NO
    <OTHER> -> AttributeExposer_2
AttributeExposer_2
    ATTR_LIST = A,B,C,D,E,F,G,H,I,J,K,L,N,P,fme_feature_type,xlsx_row_id,Q
    -> TestFilter_4
Note: Filtruje listy
TestFilter_4
    DEFAULT_VALUE = <UNFILTERED>
    PASSED_TEST_GROUP_OUTPUT = FIRST
    TEST_LIST = "BOOL_OP,OR,COMPOSITE_TEST,""""""1"""""",TEST_CLAUSE,CASE_INSENSITIVE_TEST @Value(fme_feature_type) CONTAINS SEZNAM",@Value(fme_feature_type) CONTAINS SEZNAM
    @Value(fme_feature_type) CONTAINS SEZNAM -> Odstrani_tab

Bookmark: Předúprava atributů - odstranení nev. znaků
Odstrani_tab: StringReplacer
    CASE = NO
    FIND_TEXT = "\n"
    NO_MATCH = _FME_NO_OP_
    REGEXP = NO
    SRC_ATTRS = A,C,E,xlsx_row_id,B,D,F,fme_feature_type,G,H,I,J,K,L,N
    -> Odstrani_enter
Odstrani_enter: StringReplacer
    CASE = NO
    FIND_TEXT = "    "
    NO_MATCH = _FME_NO_OP_
    REGEXP = NO
    SRC_ATTRS = A,C,E,B,D,F,fme_feature_type,G,H,I,J,K,L,N,xlsx_row_id
    -> AttributeTrimmer
AttributeTrimmer
    SRC_ATTRS = A,C,E,B,D,F,fme_feature_type,G,H,I,J,K,L,N,xlsx_row_id
    TRIM_TO_NONE = Yes
    TRIM_TYPE = Both
    -> Kontrola_hlavičky

Bookmark: Kontrola vyplnění povinných atributů v hlavičce
Kontrola_hlavičky: TestFilter
    DEFAULT_VALUE = Hlavička NOK
    PASSED_TEST_GROUP_OUTPUT = FIRST
    TEST_LIST:
      "BOOL_OP,AND,COMPOSITE_TEST,""""""1 AND 2 AND 3 AND 4 AND 5 AND 6"""""",TEST_CLAUSE,TEST @Value(xlsx_row_id) = 3
      TEST A ATTRIBUTE_HAS_A_VALUE ""
      TEST B ATTRIBUTE_HAS_A_VALUE ""
      TEST G ATTRIBUTE_HAS_A_VALUE ""
      TEST I ATTRIBUTE_HAS_A_VALUE ""
      TEST O ATTRIBUTE_HAS_A_VALUE """,Hlavička OK,"BOOL_OP,OR,COMPOSITE_TEST,""""""1"""""",TEST_CLAUSE,TEST @Value(xlsx_row_id) != 3",Data
    Hlavička OK -> AttributeCreator
    Data -> AttributeCreator_8
    Hlavička NOK -> Test_A_Typ_akce
    Hlavička NOK -> Test_B_Kod_Projektu
    Hlavička NOK -> Test_G_Popis_Akce
    Hlavička NOK -> Test_O_Zhotovitel
AttributeCreator
    ATTR_TABLE:
      SET_TO Hlavicka vyplnena = ANO
      SET_TO Merging att = 1
    -> FeatureJoiner [RIGHT]
    -> AttributeRemover
AttributeCreator_8
    ATTR_TABLE = SET_TO Merging att = 1
    -> FeatureJoiner [LEFT]
FeatureJoiner
    ATTR_CONFLICT_RES = Prefer Left
    GEOMETRY_HANDLING = Prefer Left
    JOIN_KEYS = Merging att Merging att AUTO
    JOIN_MODE = Left
    JOINED -> Tester
Tester
    BOOL_OP = OR
    TEST_CLAUSE = TEST @Value(Hlavicka vyplnena) = ANO
    TEST_MODE = TEST
    PASSED -> AttributeRemover
AttributeRemover
    REMOVE_ATTRS = Hlavicka vyplnena,numReferences
    -> TestFilter_2
Test_A_Typ_akce: Tester
    BOOL_OP = OR
    TEST_CLAUSE = TEST A ATTRIBUTE_HAS_A_VALUE ""
    TEST_MODE = TEST
    PASSED -> Test_I_Elektrarna
    FAILED -> Popis_chyby_Typ_akce
Popis_chyby_Typ_akce: AttributeCreator
    ATTR_TABLE:
      SET_TO Atribut = Typ akce
      SET_TO Hodnota atributu = Nezadáno
      SET_TO Popis chyby = Chyba hlavičky, hodnota nezadána
    -> AttributeManager_2
Test_I_Elektrarna: Tester
    BOOL_OP = OR
    TEST_CLAUSE = TEST I ATTRIBUTE_HAS_A_VALUE ""
    TEST_MODE = TEST
    FAILED -> Popis_chyby_Elektrarna
Popis_chyby_Elektrarna: AttributeCreator
    ATTR_TABLE:
      SET_TO Atribut = Elektrarna
      SET_TO Hodnota atributu = Nezadáno
      SET_TO Popis chyby = Chyba hlavičky, hodnota nezadána
    -> AttributeManager_2
Test_B_Kod_Projektu: Tester
    BOOL_OP = OR
    TEST_CLAUSE = TEST B ATTRIBUTE_HAS_A_VALUE ""
    TEST_MODE = TEST
    FAILED -> Popis_chyby_Kod_projektu
Popis_chyby_Kod_projektu: AttributeCreator
    ATTR_TABLE:
      SET_TO Atribut = Kód projektu
      SET_TO Hodnota atributu = Nezadáno
      SET_TO Popis chyby = Chyba hlavičky, hodnota nezadána
    -> AttributeManager_2
Test_G_Popis_Akce: Tester
    BOOL_OP = OR
    TEST_CLAUSE = TEST G ATTRIBUTE_HAS_A_VALUE ""
    TEST_MODE = TEST
    FAILED -> Popis_chyby_Popis_akce
Popis_chyby_Popis_akce: AttributeCreator
    ATTR_TABLE:
      SET_TO Atribut = Popis akce
      SET_TO Hodnota atributu = Nezadáno
      SET_TO Popis chyby = Chyba hlavičky, hodnota nezadána
    -> AttributeManager_2
Test_O_Zhotovitel: Tester
    BOOL_OP = OR
    TEST_CLAUSE = TEST O ATTRIBUTE_HAS_A_VALUE ""
    TEST_MODE = TEST
    FAILED -> Popis_chyby_Zhotovitel
Popis_chyby_Zhotovitel: AttributeCreator
    ATTR_TABLE:
      SET_TO Atribut = Zhotovitel
      SET_TO Hodnota atributu = Nezadáno
      SET_TO Popis chyby = Chyba hlavičky, hodnota nezadána
    -> AttributeManager_2
AttributeManager_2
    ATTR_TABLE:
      RENAME_SET_VALUE Cesta k Seznamu > Cesta elektronickeho souboru
      RENAME_SET_VALUE Název Seznamu > FileName
      RENAME_SET_VALUE xlsx_row_id > Cislo radku
      SET_TO Sheet_name = Chyby v Seznamu dokumentace
    -> AttributeKeeper_4
AttributeKeeper_4
    CREATE_BULK_MODE_FEATURES = NO
    KEEP_ATTRS = Atribut,Cesta elektronickeho souboru,FileName,Hodnota atributu,Popis chyby,Cislo radku,Sheet_name
    -> Junction_2
Note: Sorter : Input
Junction_2
    -> Junction_3

Bookmark: Příprava na kontrolu, zda jsou soubory opravdu ve složce dle Průvodky
Sampler
    RATE = 1
    SAMPLE_MODE = No
    SAMPLE_TYPE_LONG = First N Features
    SAMPLED -> FeatureReader [INITIATOR]
FeatureReader
    ATTR_ACCUM_MODE = Only Use Result
    COMBINE_GEOM = Use Initiator
    DATASET = @Substring(@Value(Cesta k Seznamu),0,@FindRegularExpression(@Value(Cesta k Seznamu),(\\)(?!.*\\),0,0,0,caseSensitive=TRUE))
    FORMAT = PATH
    OUTPUT_FEATURES_DISPLAY = Data Features
    PATH_GLOB_PATTERN = *
    PATH_NO_EMPTY_PROPERTIES = YES
    PATH_OFFSET_DATETIME = yes
    PATH_RECURSE_DIRECTORIES = YES
    PATH_RETRIEVE_FILE_PROPERTIES = NO
    PATH_TYPE = FILE
    PATH_USE_NON_STRING_ATTR = yes
    <OTHER> -> AttributeExposer
AttributeExposer
    ATTR_LIST = path_windows,path_directory_windows
    -> TestFilter
TestFilter
    DEFAULT_VALUE = Nezájmové soubory
    PASSED_TEST_GROUP_OUTPUT = FIRST
    TEST_LIST = "BOOL_OP,OR,COMPOSITE_TEST,""""""1"""""",TEST_CLAUSE,CASE_INSENSITIVE_TEST @Value(path_windows) CONTAINS \02 - Dokumenty managementu - Ostatní\",02 - Dokumenty managementu - Ostatn,"BOOL_OP,OR,COMPOSITE_TEST,""""""1"""""",TEST_CLAUSE,CASE_INSENSITIVE_TEST @Value(path_windows) CONTAINS \03 - Projektová dokumentace (PD)\",03 - Projektová dokumentace (PD),"BOOL_OP,OR,COMPOSITE_TEST,""""""1"""""",TEST_CLAUSE,CASE_INSENSITIVE_TEST @Value(path_windows) CONTAINS \04 - Technická dokumentace (TD)\",04 - Technická dokumentace (TD),"BOOL_OP,OR,COMPOSITE_TEST,""""""1"""""",TEST_CLAUSE,CASE_INSENSITIVE_TEST @Value(path_windows) CONTAINS \05 - Průvodní technická dokumentace (PTD)\",05 - Průvodní technická dokumentace (PTD),"BOOL_OP,OR,COMPOSITE_TEST,""""""1"""""",TEST_CLAUSE,CASE_INSENSITIVE_TEST @Value(path_windows) CONTAINS \06 - Dokumentace skutečného stavu (As Built)\",06 - Dokumentace skutečného stavu (As Built)
    02 - Dokumenty managementu - Ostatn -> Junction
    03 - Projektová dokumentace (PD) -> Junction
    04 - Technická dokumentace (TD) -> Junction
    05 - Průvodní technická dokumentace (PTD) -> Junction
    06 - Dokumentace skutečného stavu (As Built) -> Junction
Junction
    -> FeatureMerger_2 [SUPPLIER]

Bookmark: Zpracování hlavičky
JMA: StringSearcher
    CASE = no
    MATCHED_RESULT_ATTR = Cislo_JMA
    REGEXP = [0-9]{4}
    STRING_TO_SEARCH = @Value(B)
    MATCHED -> Lokace
Note: Nutné postupně rozšířit
Lokace: AttributeValueMapper
    DEFAULT_VALUE = Lokace není v číselníku
    DIRECTION = Forward (Source To Destination)
    LUT = PPC,PPCEPC,ELE,ELE,EPR,EPR,ETU,ETU,EGT,EGT
    SRC = I
    VAL_ATTR = Location
    -> HLAVICKA
HLAVICKA: AttributeCreator
    ATTR_TABLE:
      SET_TO Typ_akce = @Value(A)
      SET_TO Kod_projektu = @Value(B)
      SET_TO Popis_akce = @Value(G)
      SET_TO Elektrarna = @Value(I)
      SET_TO Maker = @Value(P)
      SET_TO TradePackage = @Value(Typ_akce)@Value(Cislo_JMA)
      SET_TO PackNumber = @Value(A)/@Value(Kod_projektu)
    -> TYP_AKCE_FAZE_FME
TYP_AKCE_FAZE_FME: AttributeValueMapper
    DEFAULT_VALUE = Nezadáno
    DIRECTION = Forward (Source To Destination)
    LUT = PZ,Fáze 03 - Podnikatelský záměr,ZP,Fáze 04 - Záměr projektu,PP,Fáze 05 - Příprava,RE,Fáze 06 - Realizace,JMA,Fáze 08 - JMA a rozvoj elektrárny,SKEN,Fáze 09 - Skenované dokumenty
    SRC = Typ_akce
    VAL_ATTR = Faze_FME
    -> OJ
Note: Nutné postupně rozšířit
OJ: AttributeValueMapper
    DEFAULT_VALUE = Nezadáno
    DIRECTION = Forward (Source To Destination)
    LUT = EDE,Nezadáno,EGT,Energotrans,EHO,Nezadáno,ELE,Elektrárna Ledvice,EME,Nezadáno,EPC,Nezadáno,PPC,Elektrárna PPC Počerady,EPO,Nezadáno,EPR,Elektrárna Prunéřov,TTR,Teplárna Trmice,ETU,Elektrárna Tušimice
    SRC = Elektrarna
    VAL_ATTR = OJ
    -> AttributeKeeper
AttributeKeeper
    CREATE_BULK_MODE_FEATURES = NO
    KEEP_ATTRS = Elektrarna,Kod_projektu,Popis_akce,Typ_akce,Cislo_JMA,Location,Maker,TradePackage,PackNumber,Faze_FME,OJ,Cesta k Seznamu,Název Seznamu bez prip,Název Seznamu
    -> FeatureMerger [SUPPLIER]

Bookmark: Kontrola souborů Seznam vs soubory ve složce
FeatureMerger_2
    ATTR_ACCUM_MODE = Merge Supplier
    ATTR_CONFLICT_RES = Use Requestor
    IGNORE_NULLS = No
    JOIN_KEYS = @Value(Cesta ke slozce Seznamu)@Value(Cesta elektronickeho souboru) @Value(path_windows) AUTO
    MERGE_TYPE = Attributes Only
    PROCESS_DUPS = NO
    REJECT_NULL_MISSING_KEYS = No
    SUPPLIERS_FIRST = No
    MERGED -> Podtyp_na_DCCA2A3
    UNMERGED_REQUESTOR -> AttributeKeeper_3
    UNUSED_SUPPLIER -> AttributeManager_4
AttributeKeeper_3
    CREATE_BULK_MODE_FEATURES = NO
    KEEP_ATTRS = Cislo radku,Cesta elektronickeho souboru
    -> AttributeManager_5
AttributeManager_5
    ATTR_TABLE:
      SET_TO Atribut = Cesta elektronického souboru
      SET_TO Hodnota atributu = -
      SET_TO Popis chyby = Nenalezen v adresari
      SET_TO FileName = @SubstringRegularExpression(@Value(Cesta elektronickeho souboru),(?:[^\\/](?!(\\|/)))+$,0,0,0,caseSensitive=TRUE)
      SET_TO Sheet_name = Chyby v Seznamu dokumentace
    USER_EXPOSED_ATTRIBUTES = Atribut
    -> Junction_4
AttributeManager_4
    ATTR_TABLE:
      SET_TO Cislo radku = NA
      SET_TO Atribut = NA
      SET_TO Hodnota atributu = NA
      SET_TO Popis chyby = Soubor není v Seznamu
      RENAME_SET_VALUE path_windows > Cesta elektronickeho souboru
      SET_TO FileName = @SubstringRegularExpression(@Value(Cesta elektronickeho souboru),(?:[^\\/](?!(\\|/)))+$,0,0,0,caseSensitive=TRUE)
      SET_TO Sheet_name = Chyby v Seznamu dokumentace
    -> Junction_4
Note: Chyba
Junction_4
    -> AttributeKeeper_9
AttributeKeeper_9
    CREATE_BULK_MODE_FEATURES = NO
    KEEP_ATTRS = Atribut,Cesta elektronickeho souboru,Cislo radku,FileName,Hodnota atributu,Popis chyby,Sheet_name
    -> Junction_13
Note: Sorter : Input
Junction_13
    -> Junction_14

Bookmark: Úprava a transformace dat
Podtyp_na_DCCA2A3: AttributeValueMapper
    DEFAULT_VALUE = @Value(Podtyp dokumentu)
    DIRECTION = Forward (Source To Destination)
    LUT = AZ,QA,BSCH,FA,BST,QB,DL,BC,DLI,DA,DOL,CD,DPP,DC,DPU,DC,DS,BA,DZ,WT,DÚ,WT,EO,FF,ES,AB,FA,CE,FG,FF,FO,CC,FP,FE,FSCH,FF,FSV,FS,HM,BE,IEC,EB,ISO,EB,KA,DE,KCV,TA,KS,MB,KV,FT,LI,CB,MIN,DC,MO,QC,MS,FA,MSB,LH,MSS,LD,MSV,LD,NA,CA,NKI,DC,NKO,DC,NKU,DC,NN,WA,NSS,EA,NSV,EA,NV,TA,OB,AA,OC,QC,OJ,CD,OP,CH,OPR,CB,OS,FS,OZ,BH,OŠ,CF,PA,QA,PD,CA,PDH,WT,PID,FB,PJ,CF,PK,QA,PL,BC,PM,DC,PN,BH,POD,AC,POS,QA,POZ,QC,PP,BB,PPO,BS,PPT,CA,PPV,FT,PRI,QB,PRK,QA,PRO,DE,PRS,MA,PS,FB,PSO,DB,PSYS,DB,PZ,MB,PZA,QA,PŠ,BT,RI,BE,RN,BS,RV,TB,SCHP,FT,SCHZ,MA,SD,BA,SDI,FF,SDOC,AB,SF,PF,SKV,QA,SL,FF,SM,EC,SMA,PA,SMB,EC,SML,CC,SMO,EC,SNA,FQ,SND,PB,SO,FB,SP,EC,SPD,BD,SPL,PC,SPO,MB,SPS,BG,SPV,MB,SPZ,EC,SS,EA,SSE,EC,SSI,FP,ST,PD,STR,DB,SU,PL,SVR,PD,SVS,LD,SVY,TL,SZ,EC,SČ,PB,SŠ,PB,SŽ,CB,TL,AA,TP,DF,TS,FB,TSP,EC,TZ,DD,V3D,TB,VA,DD,VB,LH,VI,DC,VKB,LH,VKS,LD,VL,ED,VP,TC,VPO,TC,VR,TB,VRH,TB,VS,LU,VSK,LC,VUB,LH,VUS,LD,VUZ,LU,VV,TC,VVK,LB,VVT,LC,VZA,LB,VZB,LH,VZD,FC,VZS,LD,ZA,QA,ZI,BS,ZK,QA,ZL,CG,ZOI,BB,ZOJ,BB,ZON,QA,ZOO,QA,ZOP,QC,ZPR,BB,ZS,MA,ZSCH,MA,ZT,MA,Zkratka,A2A3,ÚAP,LA,ÚL,AA,ÚPL,BS,ČS,FF
    SRC = Podtyp dokumentu
    VAL_ATTR = SegmentationaccordingtoCSNEN6135A3
    -> Typ_dokumentu_transformace_DM
Typ_dokumentu_transformace_DM: AttributeValueMapper
    DEFAULT_VALUE = @Value(Typ dokumentu)
    DIRECTION = Forward (Source To Destination)
    LUT = DSS,TDTT,OST,TDMR,PD,TDTD,PTD,TDPC,TD,TDOP
    SRC = Typ dokumentu
    VAL_ATTR = DocumentType
    -> PS_DPS
PS_DPS: AttributeCreator
    ATTR_TABLE:
      SET_TO PS = @Left(@Value(Oznaceni PS_DPS),2)
      SET_TO DPS = @Right(@Value(Oznaceni PS_DPS),2)
    -> AttributeManager
AttributeManager
    ATTR_TABLE:
      SET_TO AuthorDM = $(KPJM)
      RENAME_SET_VALUE Elektrarna > Code
      SET_TO CompanyIssuing = @Value(Maker)
      RENAME_SET_VALUE Datum vytvoreni > Date
      RENAME_SET_VALUE Nazev dokumentu > DocumentDescription
      SET_TO DocumentState = 20
      RENAME_SET_VALUE Doplnujici nazev predmetu_umisteni > DocumentSubject
      SET_TO DocumentSubType = AAK
      SET_TO DocumentTitle = @Value(DocumentDescription) / @Value(DocumentSubject) // @Value(Archivacni cislo dokumentu)
      RENAME_SET_VALUE Projekcni oznaceni KKS > EquipmentID
      SET_TO Id
      SET_TO ImportedDocument = true
      SET_TO OriginalDocumentVersionSeriesId
      SET_TO Phase
      SET_TO ProjectId = @Value(Location)
      RENAME_SET_VALUE Revize dokumentu > Revision
      RENAME_SET_VALUE DCC A1 > SegmentationaccordingtoCSNEN6135A1
      RENAME_SET_VALUE Pocet listu v dokumentu > Sheet
      SET_TO SO = FME_CONDITIONAL:DEFAULT_VALUE'@Value(Cislo SO)'BOOL_OP;OR;COMPOSITE_TEST;1;TEST @Value(Cislo SO) = NA''FME_NUM_CONDITIONS2___
      RENAME_SET_VALUE Archivacni cislo dokumentu > SupplierArchivalNo
      SET_TO FileName = @SubstringRegularExpression(@Value(Cesta elektronickeho souboru),(?:[^\\/](?!(\\|/)))+$,0,0,0,caseSensitive=TRUE)
      SET_TO předpříprava = \@Value(OJ)\@Value(Faze_FME)\@Value(Cislo_JMA) @Value(Popis_akce)\@SubstringRegularExpression(@Value(Cesta elektronickeho souboru),^[^\\]*,0,0,0,caseSensitive=TRUE)
      SET_TO FileNetPath = FME_CONDITIONAL:DEFAULT_VALUE'@Value(předpříprava)'BOOL_OP;OR;COMPOSITE_TEST;1;TEST Podslozka FileNetPath ATTRIBUTE_HAS_A_VALUE _FME_BLANK_STRING_'@Value(předpříprava)\@Value(Podslozka FileNetPath)'FME_NUM_CONDITIONS2___
      SET_TO FileNetPath_To_EDPPath = FME_CONDITIONAL:DEFAULT_VALUE'@SubstringRegularExpression(@Value(Cesta elektronickeho souboru),^[^\\]*,0,0,0,caseSensitive=TRUE)\@Value(FileName)'BOOL_OP;OR;COMPOSITE_TEST;1;TEST Podslozka FileNetPath ATTRIBUTE_HAS_A_VALUE _FME_BLANK_STRING_'@SubstringRegularExpression(@Value(Cesta elektronickeho souboru),^[^\\]*,0,0,0,caseSensitive=TRUE)\@Value(Podslozka FileNetPath)\@Value(FileName)'FME_NUM_CONDITIONS2___
      RENAME_SET_VALUE Cesta elektronickeho souboru > PathToFiles
      REMOVE fme_feature_type
      REMOVE Popis_akce
      REMOVE Kod_projektu
      REMOVE Typ_akce
      REMOVE Cislo_JMA
      REMOVE Faze_FME
      REMOVE OJ
      REMOVE path_windows
      REMOVE Cesta k Seznamu
      REMOVE Cesta ke slozce Seznamu
      REMOVE Název Seznamu bez prip
      REMOVE Název Seznamu
      REMOVE Poradove cislo
      REMOVE Cislo SO
      REMOVE Oznaceni PS_DPS
      REMOVE Podslozka FileNetPath
    USER_EXPOSED_ATTRIBUTES = PathToFiles,Order,Oznaceni_PS_DPS,Doplnujici_nazev_predmetu_umisteni,Stav_dokumentu,Datum_vytvoreni,Typ_dokumentu_DMDI
    -> Nahrada_carky_za_tildu

Bookmark: Dodatečná úprava EquipmentID
Nahrada_carky_za_tildu: StringReplacer
    CASE = NO
    FIND_TEXT = ,
    NO_MATCH = _FME_NO_OP_
    REGEXP = NO
    REPLACE_TEXT = ~
    SRC_ATTRS = EquipmentID
    -> Nahrada_mezery_za_nic
Nahrada_mezery_za_nic: StringReplacer
    CASE = NO
    FIND_TEXT = " "
    NO_MATCH = _FME_NO_OP_
    REGEXP = NO
    SRC_ATTRS = EquipmentID
    -> Nahrada_podtrzitka_za_nic
Nahrada_podtrzitka_za_nic: StringReplacer
    CASE = NO
    FIND_TEXT = _
    NO_MATCH = _FME_NO_OP_
    REGEXP = NO
    SRC_ATTRS = EquipmentID
    -> DateTimeConverter

Bookmark: Dodatečná úprava Date
DateTimeConverter
    DATETIME_ATTR = Date
    OUT_FORMAT = %Y-%m-%d
    PASSTHROUGH = NO
    REPAIR_INPUT = YES
    TEST_INPUT = 20200915181608
    -> DuplicateFilter_4

Bookmark: Přejmenování duplicitních souborů v Seznamu a ve složce
DuplicateFilter_4
    INPUT_ORDERED_CHOICE = No
    KEYATTR = FileNetPath_To_EDPPath
    UNIQUE -> FeatureMerger_4 [REQUESTOR]
    DUPLICATE -> FeatureMerger_4 [SUPPLIER]
FeatureMerger_4
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(FileNetPath_To_EDPPath) @Value(FileNetPath_To_EDPPath) AUTO
    MERGE_TYPE = Attributes Only
    PROCESS_DUPS = YES
    REJECT_NULL_MISSING_KEYS = No
    SUPPLIERS_FIRST = No
    MERGED -> Counter_2
    UNMERGED_REQUESTOR -> Junction_12
    USED_SUPPLIER -> Counter_2
Counter_2
    CNT_ATTR = Poradove cislo
    GROUP_BY = FileNetPath_To_EDPPath
    SCOPE = Local
    START = 1
    -> AttributeManager_9
AttributeManager_9
    ATTR_TABLE:
      SET_TO Filename_bez_extenze = @Substring(@Value(FileName),0,@FindRegularExpression(@Value(FileName),(\.)(?!.*\.),0,0,0,caseSensitive=TRUE))
      SET_TO New_PathToFiles = @ReplaceString(@Value(PathToFiles),@Value(Filename_bez_extenze),@Value(Filename_bez_extenze)_@Value(Poradove cislo),caseSensitive=TRUE)
      SET_TO New_Filename = @ReplaceString(@Value(FileName),@Value(Filename_bez_extenze),@Value(Filename_bez_extenze)_@Value(Poradove cislo),caseSensitive=TRUE)
    USER_EXPOSED_ATTRIBUTES = New_Filename,New_Cesta elektronickeho souboru,Filename_bez_extenze,Cesta elektronickeho souboru
    -> PythonCaller
Note: Změna názvu souborů ve složce
PythonCaller
    PYTHONSOURCE:
      import fme
      import fmeobjects
      import os
      import sys


      def FileRenamer(feature):
              original_file_name = feature.getAttribute('FileName')
              new_file_name = feature.getAttribute('New_Filename')
              orig_file_path = feature.getAttribute('path_directory_windows')
              new_file_path = 'dfs03.cezdata.corp\CEZ\DKE\9050060_ŘTKE\TPKE\RIZEK\JMA do DOCMAN\Testovací dávky ICC\ETU_0806_JMA\Python_test'

              os.rename(os.path.join(orig_file_path, original_file_name), os.path.join(orig_file_path, new_file_name))
    PYTHONSYMBOL = FileRenamer
    -> AttributeKeeper_10
    -> AttributeManager_10
    -> Popis_upozorneni
Note: Zmena dat v FME
AttributeManager_10
    ATTR_TABLE:
      SET_TO FileName = @Value(New_Filename)
      SET_TO PathToFiles = @Value(New_PathToFiles)
      REMOVE New_Filename
      REMOVE New_PathToFiles
      REMOVE Filename_bez_extenze
    -> Junction_12
Junction_12
    -> Counter
Popis_upozorneni: AttributeManager
    ATTR_TABLE:
      SET_TO Atribut = Název souboru
      SET_TO Hodnota atributu = "@Value(FileName)" -> "@Value(New_Filename)"
      SET_TO Popis chyby = Soubor byl přejmenován z důvodu konfliktu při zkracování složek. Došlo také k úpravě Seznamu
      SET_TO Cesta elektronickeho souboru = "@Value(PathToFiles)" -> "@Value(New_PathToFiles)"
      SET_TO FileName = @Value(New_Filename)
      SET_TO Sheet_name = Upozornění na změny v Seznamu
      SET_TO Zmena v Excelu = Ne
      REMOVE PathToFiles
      REMOVE SupplierArchivalNo
      REMOVE AuthorDM
      REMOVE Code
      REMOVE CompanyIssuing
      REMOVE Date
      REMOVE DocumentDescription
      REMOVE DocumentState
      REMOVE DocumentSubject
      REMOVE DocumentSubType
      REMOVE DocumentTitle
      REMOVE DocumentType
      REMOVE DPS
      REMOVE EquipmentID
      REMOVE Id
      REMOVE ImportedDocument
      REMOVE Location
      REMOVE Maker
      REMOVE OriginalDocumentVersionSeriesId
      REMOVE PackNumber
      REMOVE Phase
      REMOVE ProjectId
      REMOVE PS
      REMOVE Revision
      REMOVE SegmentationaccordingtoCSNEN6135A1
      REMOVE SegmentationaccordingtoCSNEN6135A3
      REMOVE Sheet
      REMOVE SO
      REMOVE TradePackage
      REMOVE předpříprava
      REMOVE FileNetPath
      REMOVE FileNetPath_To_EDPPath
      REMOVE Podtyp dokumentu
      REMOVE Typ dokumentu
      REMOVE Merging att
      REMOVE path_directory_windows
      REMOVE numReferences
      REMOVE Filename_bez_extenze
      REMOVE New_PathToFiles
      REMOVE New_Filename
      REMOVE Poradove cislo
    -> FeatureMerger_9 [REQUESTOR]
AttributeKeeper_10
    CREATE_BULK_MODE_FEATURES = NO
    KEEP_ATTRS = New_PathToFiles,PathToFiles,FileName,New_Filename
    -> FeatureMerger_5 [SUPPLIER]
FeatureReader_4
    ATTR_ACCUM_MODE = Only Use Result
    COMBINE_GEOM = Use Result
    DATASET = @Value(Cesta k Seznamu)
    FORMAT = XLSXR
    INTERACT = NONE
    OUTPUT_FEATURES_DISPLAY = Schema and Data Features
    XLSXR_ALLOW_DOLLAR_SIGNS = YES
    XLSXR_APPLY_FILTERS = No
    XLSXR_CASE_SENSITIVE_FEATURE_TYPES = YES
    XLSXR_CONFIGURATION_DATASET = \\dfs03.cezdata.corp\CEZ\DKE\9050060_ŘTKE\TPKE\RIZEK\JMA do DOCMAN\Testovací dávky ICC\ETU_0806_JMA\SEZNAM DOKUMENTACE ETU_0806_JMA.xlsm
    XLSXR_CREATE_FEATURE_TABLES_FROM_DATA = Yes
    XLSXR_EXCEL_COL_NAMES = YES
    XLSXR_EXPAND_MERGED_CELLS = Yes
    XLSXR_FORCE_DATETIME = NO
    XLSXR_QUERY_FEATURE_TYPES_FOR_MERGE_FILTERS = Yes
    XLSXR_READ_BLANK_AS = Missing
    XLSXR_READ_FORM_CONTROLS = NONE
    XLSXR_READ_RASTER_MODE = None
    XLSXR_REPLACE_ONLY_NEWLINES_CARRIAGE_RETURNS = YES
    XLSXR_SCAN_MAX_FEATURES = 1000
    XLSXR_SCHEMA = SEZNAM ETU_0806_JMA,0,A,char,20,,,1,B,char,15,,,2,C,char,18,,,3,D,char,15,,,4,E,char,17,,,5,F,char,15,,,6,G,char,71,,,7,H,char,69,,,8,I,char,75,,,9,J,char,46,,,10,K,char,26,,,11,L,char,16,,,12,M,char,15,,,13,N,char,218,,,14,O,char,12,,,15,P,char,18,,,16,Q,string,,,,1,,,,NO,NO,1,\\dfs03.cezdata.corp\CEZ\DKE\9050060_ŘTKE\TPKE\RIZEK\JMA do DOCMAN\Testovací dávky ICC\ETU_0806_JMA\SEZNAM DOKUMENTACE ETU_0806_JMA.xlsm,"0,0,16,2000",,NO,NO,Bloky,0,LOKALITA,char,4,,,1,NÁZEL,char,25,,,2,BLOK,char,7,,,3,NÁZEV,char,60,,,4,LOKALITA00,char,4,,,5,F,string,,,,6,G,string,,,,1,,,,NO,NO,1,,"0,0,6,169",,NO,NO,TYP,0,DOC_TYP,char,4,,,1,NAZEV,char,34,,,1,,,,NO,NO,1,,"0,0,1,30",,NO,NO,PODTYP,0,DOC_TYP,char,4,,,1,DOC_PODTYP,char,5,,,2,NAZEV,char,87,,,3,D,string,,,,4,E,string,,,,5,F,string,,,,6,G,string,,,,7,H,string,,,,8,I,string,,,,9,J,string,,,,10,K,string,,,,11,PD,char,4,,,12,BD,char,7,,,13,"Basic Design",char,167,,,1,,,,NO,NO,1,,"0,0,13,367",,NO,NO,STROM,0,ADRESAR,char,47,,,1,TYP,char,4,,,2,PODTYP,string,,,,3,D,char,10,,,4,PRIPONA,char,5,,,5,OBRAZ,string,,,,1,,,,NO,NO,1,,"0,0,5,22",,NO,NO,STROM/Z_30838A6A_0D16_430F_B2D5_BCB0AF2828CC__wvu_FilterData,0,ADRESAR,char,47,,,1,TYP,char,4,,,2,PODTYP,string,,,,3,D,char,10,,,1,10,0,3,NO,NO,1,,"0,0,3,10",,NO,NO
    XLSXR_SCHEMA_HANDLING_REVISION = 2
    XLSXR_SKIP_EMPTY_ROWS = YES
    XLSXR_STRIP_SHEETNAME_SPACES = YES
    XLSXR_TABLELIST = "SEZNAM ETU_0806_JMA" Bloky TYP PODTYP STROM STROM/Z_30838A6A_0D16_430F_B2D5_BCB0AF2828CC__wvu_FilterData
    XLSXR_TRIM_ATTR_NAME_WHITESPACE = Yes
    XLSXR_USE_CUSTOM_SCHEMA = NO
    <SCHEMA> -> Tester_2
    <OTHER> -> AttributeExposer_6
    INITIATOR -> AttributeKeeper_11
AttributeExposer_6
    ATTR_LIST = data_file_data,data_file_eol,data_file_line_length,data_file_line_number,data_file_type,fme_feature_type,N
    -> TestFilter_7
TestFilter_7
    DEFAULT_VALUE = <UNFILTERED>
    PASSED_TEST_GROUP_OUTPUT = FIRST
    TEST_LIST:
      "BOOL_OP,AND,COMPOSITE_TEST,""""""1 AND 2"""""",TEST_CLAUSE,CASE_INSENSITIVE_TEST @Value(fme_feature_type) CONTAINS SEZNAM
      CASE_INSENSITIVE_TEST N ATTRIBUTE_HAS_A_VALUE """,Řádky s elektronickou cestou,"BOOL_OP,OR,COMPOSITE_TEST,""""""1"""""",TEST_CLAUSE,CASE_INSENSITIVE_TEST @Value(fme_feature_type) CONTAINS STROM/",Špatný list, vynechám
    Řádky s elektronickou cestou -> FeatureMerger_5 [REQUESTOR]
FeatureMerger_5
    ATTR_ACCUM_MODE = Merge Supplier
    ATTR_CONFLICT_RES = Use Requestor
    IGNORE_NULLS = No
    JOIN_KEYS = @Value(N) @Value(PathToFiles) AUTO
    MERGE_TYPE = Attributes Only
    PROCESS_DUPS = NO
    REJECT_NULL_MISSING_KEYS = No
    SUPPLIERS_FIRST = No
    MERGED -> AttributeManager_11
AttributeManager_11
    ATTR_TABLE:
      SET_TO N = @Value(New_PathToFiles)
      REMOVE New_PathToFiles
      REMOVE PathToFiles
    -> Junction_9
Junction_9
    -> Counter_3
Counter_3
    CNT_ATTR = Poradi
    DOMAIN = counter
    SCOPE = Global
    START = 2
    -> Sorter_3
AttributeKeeper_11
    CREATE_BULK_MODE_FEATURES = NO
    KEEP_ATTRS = Název Seznamu
    -> FeatureMerger_7 [SUPPLIER]
Tester_2
    BOOL_OP = OR
    TEST_CLAUSE = CASE_INSENSITIVE_TEST @Value(fme_feature_type_name) BEGINS_WITH STROM/
    TEST_MODE = TEST
    FAILED -> AttributeCreator_5
AttributeCreator_5
    ATTR_TABLE = SET_TO Poradi = 1
    -> Sorter_3
Sorter_3
    SORT_PARM = Poradi NUMERIC ASCENDING
    SORTED -> FeatureMerger_7 [REQUESTOR]
FeatureMerger_7
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> FeatureWriter_3 [Output]
Note: Zápis změny "Cesty elektronického souboru" do Seznamu
FeatureWriter_3
    DATASET = $(Pevna_cesta)\$(Slozka)\@Value(Název Seznamu)
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_DESTINATION_DATASETTYPE_VALIDATION = Yes
    XLSXW_DROP_TABLE = No
    XLSXW_FIELD_NAMES_FORMATTING = Yes
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TEMPLATEFILE = @Value(Cesta k Seznamu)
    XLSXW_TRUNCATE_TABLE = No
    XLSXW_WRITER_MODE = Insert
    SUMMARY -> Popis_upozorneni_2
Popis_upozorneni_2: AttributeManager
    ATTR_TABLE:
      SET_TO Zmena v Excelu = Ano
      REMOVE _feature_types{}.count
      REMOVE _feature_types{}.name
      REMOVE _dataset
      REMOVE _total_features_written
    -> FeatureMerger_9 [SUPPLIER]
FeatureMerger_9
    ATTR_ACCUM_MODE = Merge Supplier
    ATTR_CONFLICT_RES = Use Supplier
    IGNORE_NULLS = No
    JOIN_KEYS = 1 1 AUTO
    MERGE_TYPE = Attributes Only
    PROCESS_DUPS = NO
    REJECT_NULL_MISSING_KEYS = No
    SUPPLIERS_FIRST = No
    MERGED -> Tester_4
Tester_4
    BOOL_OP = OR
    TEST_CLAUSE = TEST @Value(Zmena v Excelu) = Ano
    TEST_MODE = TEST
    PASSED -> Junction_10
    FAILED -> AttributeManager_12
AttributeManager_12
    ATTR_TABLE:
      SET_TO Popis chyby = Chyba  zapisu PathToFiles do Excelu
      SET_TO Sheet_name = @Value(Zmena v Excelu)
    -> Junction_10
Note: Sorter : Input
Junction_10
    -> Junction_11

Bookmark: Multicontent
Counter
    CNT_ATTR = Count
    DOMAIN = counter
    SCOPE = Global
    START = 0
    -> AttributeKeeper_6
    -> FeatureMerger_8 [SUPPLIER]
AttributeKeeper_6
    CREATE_BULK_MODE_FEATURES = NO
    KEEP_ATTRS = SupplierArchivalNo,FileName,PathToFiles,FileNetPath,Count
    -> AttributeCreator_3
AttributeCreator_3
    ATTR_TABLE = SET_TO Extenze = @Substring(@Value(FileName),@add(@FindRegularExpression(@Value(FileName),(\.)(?!.*\.),0,0,0,caseSensitive=TRUE),1))
    -> AttributeValueMapper
AttributeValueMapper
    DEFAULT_VALUE = 5
    LUT = PDF,1,pdf,1,DOCX,2,docx,2,DOC,2,doc,2
    MAPPING_DIRECTION = FORWARD
    SRC = Extenze
    VAL_ATTR = Priorita extenze
    -> Sorter_2
Sorter_2
    SORT_PARM = Priorita extenze NUMERIC ASCENDING
    SORTED -> DuplicateFilter_2
DuplicateFilter_2
    INPUT_ORDERED_CHOICE = No
    KEYATTR = SupplierArchivalNo FileNetPath
    UNIQUE -> FeatureMerger_6 [REQUESTOR]
    DUPLICATE -> FeatureMerger_6 [SUPPLIER]
    DUPLICATE -> DuplicateFilter_3
FeatureMerger_6
    ATTR_ACCUM_MODE = Prefix Supplier
    IGNORE_NULLS = No
    JOIN_KEYS = @Value(SupplierArchivalNo) @Value(SupplierArchivalNo) AUTO @Value(FileNetPath) @Value(FileNetPath) AUTO
    LIST_ATTRS_TO_INCLUDE = FileName PathToFiles
    LIST_NAME = Multicontent
    MERGE_TYPE = Attributes Only
    PROCESS_DUPS = NO
    REJECT_NULL_MISSING_KEYS = No
    SUPPLIERS_FIRST = No
    SUPPLIER_PREFIX = Dup_
    MERGED -> ListConcatenator
    UNMERGED_REQUESTOR -> AttributeKeeper_8
ListConcatenator
    DROP_EMPTY_PARTS = Yes
    LIST_ATTR = Multicontent{}.FileName
    SEP = ~
    VAL_ATTR = FileName_Multi
    -> ListConcatenator_2
ListConcatenator_2
    DROP_EMPTY_PARTS = Yes
    LIST_ATTR = Multicontent{}.PathToFiles
    SEP = ~
    VAL_ATTR = PathToFiles_Multi
    -> AttributeManager_8
AttributeManager_8
    ATTR_TABLE:
      SET_TO FileName = @Value(FileName)~@Value(FileName_Multi)
      SET_TO PathToFiles = @Value(PathToFiles)~@Value(PathToFiles_Multi)
    USER_EXPOSED_ATTRIBUTES = FileNetPath,Filename_raw,Dup_FileNetPath,Dup_Filename_raw,path_directory_windows,Dup_path_directory_windows
    -> AttributeKeeper_8
AttributeKeeper_8
    CREATE_BULK_MODE_FEATURES = NO
    KEEP_ATTRS = FileName,PathToFiles,SupplierArchivalNo,Count
    -> FeatureMerger_8 [REQUESTOR]
FeatureMerger_8
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(Count) @Value(Count) AUTO
    MERGE_TYPE = Attributes Only
    PROCESS_DUPS = YES
    REJECT_NULL_MISSING_KEYS = No
    SUPPLIERS_FIRST = No
    MERGED -> Test_ciselniku_DCC_A2A3_2 [REQUESTOR]
DuplicateFilter_3
    INPUT_ORDERED_CHOICE = No
    KEYATTR = SupplierArchivalNo FileNetPath

Bookmark: New Bookmark
Test_ciselniku_DCC_A2A3_2: FeatureMerger
    ATTR_ACCUM_MODE = Merge Supplier
    ATTR_CONFLICT_RES = Use Requestor
    IGNORE_NULLS = No
    JOIN_KEYS = @Value(SegmentationaccordingtoCSNEN6135A3) @Value(value) AUTO
    MERGE_TYPE = Attributes Only
    PROCESS_DUPS = NO
    REJECT_NULL_MISSING_KEYS = Yes
    SUPPLIERS_FIRST = No
    MERGED -> Test_ciselniku_DCC_A1 [REQUESTOR]
    UNMERGED_REQUESTOR -> Popis_chyby_DCC_A2_A3_2
    UNMERGED_REQUESTOR -> Test_ciselniku_DCC_A1 [REQUESTOR]
    <REJECTED> -> Popis_chyby_DCC_A2_A3_2
    <REJECTED> -> Test_ciselniku_DCC_A1 [REQUESTOR]
Note: Rozlišuje missing a mimo číselník
Popis_chyby_DCC_A2_A3_2: AttributeCreator
    ATTR_TABLE:
      SET_TO Atribut = Podtyp dokumentu
      SET_TO Hodnota atributu = FME_CONDITIONAL:DEFAULT_VALUE'Nezadáno'BOOL_OP;OR;COMPOSITE_TEST;1;TEST SegmentationaccordingtoCSNEN6135A3 ATTRIBUTE_HAS_A_VALUE _FME_BLANK_STRING_'@Value(Podtyp dokumentu)'FME_NUM_CONDITIONS2___
      SET_TO Popis chyby = FME_CONDITIONAL:DEFAULT_VALUE'Hodnota nezadána'BOOL_OP;OR;COMPOSITE_TEST;1;TEST SegmentationaccordingtoCSNEN6135A3 ATTRIBUTE_HAS_A_VALUE _FME_BLANK_STRING_'Hodnota není v číselníku'FME_NUM_CONDITIONS2___
      SET_TO Cesta elektronickeho souboru = @Value(PathToFiles)
      SET_TO Sheet_name = Chyby v Seznamu dokumentace
    -> DuplicateFilter

Bookmark: New Bookmark
Test_ciselniku_DCC_A1: FeatureMerger
    ATTR_ACCUM_MODE = Merge Supplier
    ATTR_CONFLICT_RES = Use Requestor
    IGNORE_NULLS = No
    JOIN_KEYS = @Value(SegmentationaccordingtoCSNEN6135A1) @Value(value) AUTO
    MERGE_TYPE = Attributes Only
    PROCESS_DUPS = NO
    REJECT_NULL_MISSING_KEYS = Yes
    SUPPLIERS_FIRST = No
    MERGED -> Test_ciselniku_Doc_Type [REQUESTOR]
    UNMERGED_REQUESTOR -> Popis_chyby_DCC_A1_2
    UNMERGED_REQUESTOR -> Test_ciselniku_Doc_Type [REQUESTOR]
    <REJECTED> -> Popis_chyby_DCC_A1_2
    <REJECTED> -> Test_ciselniku_Doc_Type [REQUESTOR]
Note: Rozlišuje missing a mimo číselník
Popis_chyby_DCC_A1_2: AttributeCreator
    ATTR_TABLE:
      SET_TO Atribut = DCC A1
      SET_TO Hodnota atributu = FME_CONDITIONAL:DEFAULT_VALUE'Nezadáno'BOOL_OP;OR;COMPOSITE_TEST;1;TEST SegmentationaccordingtoCSNEN6135A1 ATTRIBUTE_HAS_A_VALUE _FME_BLANK_STRING_'@Value(SegmentationaccordingtoCSNEN6135A1)'FME_NUM_CONDITIONS2___
      SET_TO Popis chyby = FME_CONDITIONAL:DEFAULT_VALUE'Hodnota nezadána'BOOL_OP;OR;COMPOSITE_TEST;1;TEST SegmentationaccordingtoCSNEN6135A1 ATTRIBUTE_HAS_A_VALUE _FME_BLANK_STRING_'Hodnota není v číselníku'FME_NUM_CONDITIONS2___
      SET_TO Cesta elektronickeho souboru = @Value(PathToFiles)
      SET_TO Sheet_name = Chyby v Seznamu dokumentace
    -> DuplicateFilter

Bookmark: New Bookmark
Test_ciselniku_Doc_Type: FeatureMerger
    ATTR_ACCUM_MODE = Merge Supplier
    ATTR_CONFLICT_RES = Use Requestor
    IGNORE_NULLS = No
    JOIN_KEYS = @Value(DocumentType) @Value(value) AUTO
    MERGE_TYPE = Attributes Only
    PROCESS_DUPS = NO
    REJECT_NULL_MISSING_KEYS = Yes
    SUPPLIERS_FIRST = No
    MERGED -> Test_ciselniku_Doc_SubType [REQUESTOR]
    UNMERGED_REQUESTOR -> Popis_chyby_Typ_dokumentu_2
    UNMERGED_REQUESTOR -> Test_ciselniku_Doc_SubType [REQUESTOR]
    <REJECTED> -> Popis_chyby_Typ_dokumentu_2
    <REJECTED> -> Test_ciselniku_Doc_SubType [REQUESTOR]
Note: Rozlišuje missing a mimo číselník
Popis_chyby_Typ_dokumentu_2: AttributeCreator
    ATTR_TABLE:
      SET_TO Atribut = Typ dokumentu
      SET_TO Hodnota atributu = FME_CONDITIONAL:DEFAULT_VALUE'Nezadáno'BOOL_OP;OR;COMPOSITE_TEST;1;TEST Typ dokumentu ATTRIBUTE_HAS_A_VALUE _FME_BLANK_STRING_'@Value(Typ dokumentu)'FME_NUM_CONDITIONS2___
      SET_TO Popis chyby = FME_CONDITIONAL:DEFAULT_VALUE'Hodnota nezadána'BOOL_OP;OR;COMPOSITE_TEST;1;TEST Typ dokumentu ATTRIBUTE_HAS_A_VALUE _FME_BLANK_STRING_'Hodnota není v číselníku'FME_NUM_CONDITIONS2___
      SET_TO Cesta elektronickeho souboru = @Value(PathToFiles)
      SET_TO Sheet_name = Chyby v Seznamu dokumentace
    -> DuplicateFilter

Bookmark: New Bookmark
Test_ciselniku_Doc_SubType: FeatureMerger
    ATTR_ACCUM_MODE = Merge Supplier
    ATTR_CONFLICT_RES = Use Requestor
    IGNORE_NULLS = No
    JOIN_KEYS = @Value(DocumentSubType) @Value(value) AUTO
    MERGE_TYPE = Attributes Only
    PROCESS_DUPS = NO
    REJECT_NULL_MISSING_KEYS = No
    SUPPLIERS_FIRST = No
    MERGED -> Junction_6
    UNMERGED_REQUESTOR -> Popis_chyby_SubType_2
    UNMERGED_REQUESTOR -> Junction_6
    <REJECTED> -> Popis_chyby_SubType_2
    <REJECTED> -> Junction_6
Popis_chyby_SubType_2: AttributeCreator
    ATTR_TABLE:
      SET_TO Atribut = DocumentSubType
      SET_TO Hodnota atributu = @Value(DocumentSubType)
      SET_TO Popis chyby = Hodnota neni v číselníku
      SET_TO Cesta elektronickeho souboru = @Value(PathToFiles)
      SET_TO Sheet_name = Chyby v Seznamu dokumentace
    -> DuplicateFilter

Bookmark: Kontrola dle číselníků nebo pravidel
Junction_6
    -> Test_delky_zaslozkovani_2
DuplicateFilter
    INPUT_ORDERED_CHOICE = No
    KEYATTR = Cislo radku
    UNIQUE -> FeatureMerger_3 [SUPPLIER]
    UNIQUE -> AttributeKeeper_2
    DUPLICATE -> AttributeKeeper_2
Note: Odebere chybové záznamy
FeatureMerger_3
    ATTR_ACCUM_MODE = Merge Supplier
    ATTR_CONFLICT_RES = Use Requestor
    IGNORE_NULLS = No
    JOIN_KEYS = @Value(Cislo radku) @Value(Cislo radku) AUTO
    MERGE_TYPE = Attributes Only
    PROCESS_DUPS = NO
    REJECT_NULL_MISSING_KEYS = No
    SUPPLIERS_FIRST = No
    UNMERGED_REQUESTOR -> StringReplacer
Note: Všechny chybové záznamy
AttributeKeeper_2
    CREATE_BULK_MODE_FEATURES = NO
    KEEP_ATTRS = Atribut,FileName,Hodnota atributu,Popis chyby,Cislo radku,Cesta elektronickeho souboru,FileNetPath_To_EDPPath,Sheet_name
    -> Sorter

Bookmark: New Bookmark
Note: Kontrola na délku cesty FileNetPath_To_EDPPath < 240 zn; Sheet < 9 zn
Test_delky_zaslozkovani_2: TestFilter
    DEFAULT_VALUE = <UNFILTERED>
    PASSED_TEST_GROUP_OUTPUT = FIRST
    TEST_LIST = "BOOL_OP,OR,COMPOSITE_TEST,""""""1"""""",TEST_CLAUSE,TEST @Evaluate(@StringLength(@Value(FileNetPath_To_EDPPath))) <= 200",Delka FileNetPath_To_EDPPath <=200
    Delka FileNetPath_To_EDPPath <=200 -> FeatureMerger_3 [REQUESTOR]
    <UNFILTERED> -> Popis_chyby_SubType_3
    <UNFILTERED> -> FeatureMerger_3 [REQUESTOR]
Popis_chyby_SubType_3: AttributeCreator
    ATTR_TABLE:
      SET_TO Atribut = DocumentSubType
      SET_TO Hodnota atributu = @Value(DocumentSubType)
      SET_TO Popis chyby = Hodnota neni v číselníku
      SET_TO Cesta elektronickeho souboru = @Value(PathToFiles)
      SET_TO Sheet_name = Chyby v Seznamu dokumentace
    -> DuplicateFilter

Bookmark: Tvorba řádku pro Seznam
AttributeManager_3
    ATTR_TABLE:
      SET_TO AuthorDM = $(KPJM)
      RENAME_SET_VALUE Elektrarna > Code
      RENAME_SET_VALUE Maker > CompanyIssuing
      SET_TO Date = @DateTimeFormat(@DateTimeNow(),%Y-%m-%d)
      SET_TO DocumentState = 20
      SET_TO DocumentSubType = AAK
      RENAME_SET_VALUE Název Seznamu bez prip > DocumentTitle
      SET_TO DocumentType = TDMM
      SET_TO ImportedDocument = true
      SET_TO ProjectId = @Value(Location)
      SET_TO SegmentationaccordingtoCSNEN6135A1 = B
      SET_TO SegmentationaccordingtoCSNEN6135A3 = AB
      RENAME_SET_VALUE Název Seznamu > FileName
      SET_TO FileNetPath = \@Value(OJ)\@Value(Faze_FME)\@Value(Cislo_JMA) @Value(Popis_akce)
      SET_TO PathToFiles = @Value(FileName)
      REMOVE Popis_akce
      REMOVE Kod_projektu
      REMOVE Typ_akce
      REMOVE Cislo_JMA
      REMOVE Faze_FME
      REMOVE OJ
      REMOVE numReferences
      REMOVE PackNumber
      REMOVE Cesta k Seznamu
    USER_EXPOSED_ATTRIBUTES = PathToFiles,Order,Oznaceni_PS_DPS,Doplnujici_nazev_predmetu_umisteni,Stav_dokumentu,Datum_vytvoreni,Typ_dokumentu_DMDI
    -> StringReplacer

Bookmark: Writers
Note: "@SubstringRegularExpression(@Value(Cesta k Seznamu),^(.*[\\\/]),0,0,0,caseSensitive=TRUE)"
FeatureWriter
    CSV2_COORDINATE_SYSTEM_GRANULARITY = FEATURE_TYPE
    CSV2_DELIMITER = ;
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(Pevna_cesta)\$(Slozka)
    DATASET_ATTR = _dataset
    FEATURE_TYPE_LIST_ATTR = _feature_types
    FORMAT = CSV2
    TOTAL_FEATURES_WRITTEN_ATTR = _total_features_written
Note: "@SubstringRegularExpression(@Value(Cesta k Seznamu),^(.*[\\\/]),0,0,0,caseSensitive=TRUE)\Report.xlsx"
FeatureWriter_2
    DATASET = $(Pevna_cesta)\$(Slozka)\Report_t.xlsx
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_DESTINATION_DATASETTYPE_VALIDATION = Yes
    XLSXW_DROP_TABLE = Yes
    XLSXW_FIELD_NAMES_FORMATTING = Yes
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TRUNCATE_TABLE = Yes
    XLSXW_WRITER_MODE = Insert
