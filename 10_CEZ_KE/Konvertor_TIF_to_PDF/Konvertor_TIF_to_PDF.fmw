FME workspace Konvertor_TIF_to_PDF.fmw

Parameters:
- FME_JOB_ID = 303   # FME Flow Job ID
- FME_SHAREDRESOURCE_TEMP = C:\Users\zdeborjan\OneDrive - Skupina ČEZ\FME\06_Pomocne workbenche\Skeny   # FME Flow Temporary Resource Directory

Note: Vybere vždy jen jeden soubor, Status od 1 do 5
SQLCreator
    DATASET = PG_DOKE
    EXPOSED_ATTRIBUTE_LIST = ID,path_directory_windows,path_rootname,path_extension,Status
    FORMAT = POSTGRES
    OUTPUT_FEATURES_DISPLAY = Data Features
    POSTGRES_CREATE_FEATURE_TABLES_FROM_DATA = Yes
    POSTGRES_NAMED_CONNECTION = PG_DOKE
    POSTGRES_QUERY_FEATURE_TYPES_FOR_MERGE_FILTERS = Yes
    POSTGRES_READ_TIME_WITH_TIMEZONE = Yes
    POSTGRES_SCHEMAS_FOR_TABLE_LISTING = public
    SQL_STATEMENT:
      SELECT 	"ID",
      		path_directory_windows,
      		path_rootname,
      		path_extension,
      		"Status"
      FROM public."FME_SKENY_Seznam_souboru"
      where "Status" between 1 and 5
      order by "Status" asc
      limit 1
    RESULT -> SQLExecutor [INITIATOR]
    RESULT -> FeatureMerger [SUPPLIER]
Note: Označení zpracovávaného souboru v DB
SQLExecutor
    ATTR_IGNORE_NULLS = Yes
    COMBINE_ATTRS = Keep Initiator Attributes if Conflict
    COMBINE_GEOM = Initiator Geometry Only
    DATASET = PG_DOKE
    FORMAT = POSTGRES
    OUTPUT_FEATURES_DISPLAY = Schema and Data Features
    POSTGRES_CREATE_FEATURE_TABLES_FROM_DATA = Yes
    POSTGRES_NAMED_CONNECTION = PG_DOKE
    POSTGRES_QUERY_FEATURE_TYPES_FOR_MERGE_FILTERS = Yes
    POSTGRES_READ_TIME_WITH_TIMEZONE = Yes
    POSTGRES_SCHEMAS_FOR_TABLE_LISTING = public
    SQL_STATEMENT:
      Update public."FME_SKENY_Seznam_souboru"
      SET "Last_JobID" = -$(FME_JOB_ID)
      where "ID" = @Value(ID)
    INITIATOR -> FeatureReader_2 [INITIATOR]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> SQLExecutor_2 [INITIATOR]
Note: Označení zpracovávaného souboru v DB
SQLExecutor_2
    ATTR_IGNORE_NULLS = Yes
    COMBINE_ATTRS = Keep Initiator Attributes if Conflict
    COMBINE_GEOM = Initiator Geometry Only
    DATASET = PG_DOKE
    FORMAT = POSTGRES
    OUTPUT_FEATURES_DISPLAY = Schema and Data Features
    POSTGRES_CREATE_FEATURE_TABLES_FROM_DATA = Yes
    POSTGRES_NAMED_CONNECTION = PG_DOKE
    POSTGRES_QUERY_FEATURE_TYPES_FOR_MERGE_FILTERS = Yes
    POSTGRES_READ_TIME_WITH_TIMEZONE = Yes
    POSTGRES_SCHEMAS_FOR_TABLE_LISTING = public
    SQL_STATEMENT:
      Update public."FME_SKENY_Seznam_souboru"
      SET "Last_JobID" = $(FME_JOB_ID), "Status" = "Status" + 1
      where "ID" = @Value(ID)

Bookmark: Načtení tiff a uložení tiff s kompresí
FeatureReader_2
    ATTRIBUTES = TIFF,
    ATTR_ACCUM_MODE = Merge Initiator and Result
    ATTR_CONFLICT_RES = Use Result
    ATTR_IGNORE_NULLS = No
    COMBINE_GEOM = Use Result
    DATASET = @Value(path_directory_windows)\@Value(path_rootname).@Value(path_extension)
    FORMAT = TIFF
    INTERACT = NONE
    ORDER_RESULTS = No
    OUTPUT_FEATURES_DISPLAY = Schema and Data Features
    TIFF_FEATURE_TYPE_NAME = FORMAT_NAME
    TIFF_LENIENT_READ = Yes
    TIFF_READER_META_ATTRIBUTES = fme_dataset fme_basename
    TIFF_USE_SEARCH_ENVELOPE = NO
    TIFF -> RasterPaletteResolver
RasterPaletteResolver
    -> RasterResampler
RasterResampler
    INTERPOLATION_TYPE_NAME = Bicubic
    PERCENTAGE = 55
    ROWCOL_OR_CELLSIZE = Percentage
    RESAMPLED -> FeatureWriter_2 [TIFF]
FeatureWriter_2
    DATASET = $(FME_SHAREDRESOURCE_TEMP)\Skeny
    DATASET_ATTR = _dataset
    FEATURE_TYPE_LIST_ATTR = _feature_types
    FORMAT = JPEG
    JPEG_COORDINATE_SYSTEM_GRANULARITY = FEATURE
    MORE_SUMMARY_ATTRS = ID path_directory_windows path_extension path_rootname Status
    SELECTED_PORTS = TIFF
    TOTAL_FEATURES_WRITTEN_ATTR = _total_features_written
    SUMMARY -> FeatureReader_4 [INITIATOR]
    SUMMARY -> FeatureHolderExt [Keep]

Bookmark: Načtení souborů ve složce a přeuložení jako PDF
FeatureReader_4
    ATTRIBUTES = JPEG,
    ATTR_ACCUM_MODE = Merge Initiator and Result
    ATTR_CONFLICT_RES = Use Result
    ATTR_IGNORE_NULLS = No
    COMBINE_GEOM = Use Result
    DATASET = @Value(_dataset)\@Value(_feature_types{0}.name).jpg
    FORMAT = JPEG
    INTERACT = NONE
    JPEG_ALL_ATTRS_STARTING_WITH_EXIF_ARE_FORMAT_ATTRS = YES
    JPEG_APPLY_EXIF_ORIENTATION = Yes
    JPEG_APPLY_GCPS = NO
    JPEG_FORMAT_RATIONAL_AS_FRACTION = No
    JPEG_GROUP_BY_DATASET = No
    JPEG_READER_META_ATTRIBUTES = fme_dataset fme_basename
    JPEG_USE_SEARCH_ENVELOPE = NO
    ORDER_RESULTS = No
    OUTPUT_FEATURES_DISPLAY = Schema and Data Features
    JPEG -> RasterInterpretationCoercer_2
RasterInterpretationCoercer_2
    COLOR_TO_COLOR = Scale by data type
    FLOAT_TO_INTEGER = Round
    INTERPRETATION = RGB24
    NUMERIC_TO_COLOR = Scale by data values
    RGBA_TO_RGB = Drop the alpha band
    -> BoundsExtractor_3
BoundsExtractor_3
    XMAX = _xmax
    XMIN = _xmin
    YMAX = _ymax
    YMIN = _ymin
    ZMAX = _zmax
    ZMIN = _zmin
    -> AttributeManager_6
AttributeManager_6
    ATTR_TABLE:
      SET_TO pdf_page_number = 1
      SET_TO pomer = @Evaluate(@abs(@Value(_xmax)/@Value(_ymin)))
      SET_TO sirka = 3370
      SET_TO vyska = @Evaluate(@round(@Value(sirka)/@Value(pomer),0))
      SET_TO sirka_bod = 14931
      SET_TO vyska_bod = @Evaluate(@round(@Value(sirka_bod)/@Value(pomer),0))
    -> PDFPageFormatter_3 [New Object]
PDFPageFormatter_3
    PAGE_HEIGHT_PTS = 2383
    PAGE_HEIGHT_USER = 33.1
    PAGE_NUMBER = 1
    PAGE_OBJECTS = "New Object MINX;0;CLIPPING_ENABLED;No;FIXED_ASPECT;Yes;SIZE_PARAMS;;SCALING_PARAMS;;HEIGHT;2383.2;MINY;-0.199951;WIDTH;3369.6"
    PAGE_ORIENTATION = Landscape
    PAGE_SIZE = A0
    PAGE_UNITS = Inches
    PAGE_WIDTH_PTS = 3370
    PAGE_WIDTH_USER = 46.8
    -> AttributeManager_5
AttributeManager_5
    ATTR_TABLE:
      SET_TO pdf_frame_rectangle = 0 0 @Value(sirka) @Value(vyska)
      SET_TO pdf_world_rectangle = 0 @Value(_ymin) @Value(_xmax) 0
      SET_TO pdf_page_size = @Value(sirka) @Value(vyska)
      RENAME_SET_VALUE fme_basename > path_rootname
    -> FeatureWriter [TIFF]
FeatureWriter
    DATASET = @Value(_feature_types{0}.path_directory_windows)\@Value(_feature_types{0}.path_rootname).pdf
    DATASET_ATTR = _dataset
    FEATURE_TYPE_LIST_ATTR = _feature_types
    FORMAT = PDF2D
    PDF2D_COMPRESS_STREAMS = Yes
    PDF2D_DEFAULT_LINE_WIDTH = 1.0
    PDF2D_DEFAULT_OPACITY = 0.4
    PDF2D_DEFAULT_POINT_SIZE = 1.0
    PDF2D_DESTINATION_DATASETTYPE_VALIDATION = Yes
    PDF2D_PAGE_SIZE = Letter
    PDF2D_PANEL_VISIBILITY = None
    PDF2D_PDF14_COMPATIBLE = Yes
    PDF2D_RANDOMIZE_FEATURE_TYPE_COLOR = No
    PDF2D_RICH_TEXT = No
    PDF2D_SCALE_TEXT_FONT = No
    PDF2D_WRITE_ATTRIBUTES = No
    TOTAL_FEATURES_WRITTEN_ATTR = _total_features_written
    SUMMARY -> FeatureHolderExt [Discard]
FeatureHolderExt
    Kept -> FileDeleter
FileDeleter
    FileToDelete = @Value(_dataset)\@Value(_feature_types{0}.name).jpg
    -> FeatureMerger [REQUESTOR]

FME custom transformer FeatureHolderExt
FeatureHolder Extended.
All input features cause hold but only those on the 'keep' port are passed to the output. Those on 'discard' are not passed through.
FeatureHolder Extended.
All input features cause hold but only those on the 'keep' port are passed to the output. Those on 'discard' are not passed through.

Keep (input)
    -> FeatureHolder
Discard (input)
    -> AttributeCreator
AttributeCreator
    ATTR_TABLE = SET_TO markForDiscard = t
    -> FeatureHolder
FeatureHolder
    -> isKept
isKept: Tester
    BOOL_OP = OR
    TEST_CLAUSE = TEST markForDiscard ATTRIBUTE_IS_MISSING ""
    TEST_MODE = Automatic
    PASSED -> AttributeRemover
AttributeRemover
    REMOVE_ATTRS = markForDiscard
    -> Kept (output)
Kept (output)

FME custom transformer FileDeleter
Delete specified file - not using Python, but rather the FeatureWriter - Copy File approach to remove the file. 
Image by OpenClipart-Vectors from Pixabay

Parameters:
- FileToDelete =   # File to delete (full path including filename)

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    SUMMARY -> Output (output)
Output (output)
