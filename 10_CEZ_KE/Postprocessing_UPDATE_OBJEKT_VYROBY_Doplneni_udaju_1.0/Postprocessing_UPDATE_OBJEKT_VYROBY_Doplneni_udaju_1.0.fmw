FME workspace Postprocessing_UPDATE_OBJEKT_VYROBY_Doplneni_udaju_1.0.fmw
Title: COZ_Projekt_Doplneni_udaju_ku_obec_okres_kraj_stav-urad
History: 29.3.2023,JH,Verze se seznamem ku, obcí, okresů, krajů, stav. úřadů podle celého polygonu projektu

Creator
    COORDSYS = Czech/JTSK.Krovak
    GEOMTYPE = Geometry Object
    NUM = 1
    CREATED -> FeatureReader_2 [INITIATOR]
    CREATED -> FeatureReader_3 [INITIATOR]
FeatureReader_2
    ATTRIBUTES = GISDVTB.CIS_OBJEKT_VYROBY,"FID,ORIENTATION,Z,QUALITY,SHORT_VALUE,VALUE,DATE_OF_CREATION,ID_TYP_OBJ_VYR,ID_ELEKTRARNA,ID_OJ,PSK_SUBFACILITY_CODE,NUTS,ID_ACTIVE,NUTS_CEZ,DOCMAN_CODE,ID,SPP_CEZ,ID_STAV,KOD_IS_VYROBA,ID_TIPOM"
    ATTR_ACCUM_MODE = Only Use Result
    COMBINE_GEOM = Use Result
    COORDSYS = Czech/JTSK.Krovak
    DATASET = vyrokp_GISDVTB
    FEATURETYPES = GISDVTB.CIS_OBJEKT_VYROBY
    FORMAT = ORACLE_SPATIAL
    INTERACT = NONE
    ORACLE_SPATIAL_CHUNK_SIZE = 200
    ORACLE_SPATIAL_CREATE_FEATURE_TABLES_FROM_DATA = Yes
    ORACLE_SPATIAL_HANDLE_MULTIPLE_SPATIAL_COLUMNS = NO
    ORACLE_SPATIAL_NAMED_CONNECTION = vyrokp_GISDVTB
    ORACLE_SPATIAL_PARSE_MAPINFO_SYMBOLOGY = NO
    ORACLE_SPATIAL_PERSISTENT_CONNECTION = YES
    ORACLE_SPATIAL_QUERY_FEATURE_TYPES_FOR_MERGE_FILTERS = Yes
    ORACLE_SPATIAL_READ_3D_POLYGON_AS_FACE = NO
    ORACLE_SPATIAL_REMOVE_SCHEMA_QUALIFIER = NO
    ORACLE_SPATIAL_SERVER_TYPE = ORACLE8i
    ORACLE_SPATIAL_SHOW_SYSTEM_TABLES = NO
    ORACLE_SPATIAL_USE_SEARCH_ENVELOPE = NO
    ORACLE_SPATIAL_USE_UNIFIED_DATE_ATTRS = YES
    OUTPUT_FEATURES_DISPLAY = Data Features
    GISDVTB.CIS_OBJEKT_VYROBY -> ChangeDetector [ORIGINAL]
    GISDVTB.CIS_OBJEKT_VYROBY -> SpatialFilter [Candidate]
SpatialFilter
    AGGREGATE_HANDLING = Yes
    ATTR_ACCUM_MODE = Merge Filter
    ATTR_CONFLICT_RES = Use Filter
    BASE_TYPE = Multiple Filters
    CURVE_BOUNDARY_RULE_PARAM = Default Rule
    PASS_CRITERIA = Pass Against One Filter
    PREDATTR = _predicate
    PREDICATES = INTERSECTS
    USE_BOUNDING_BOX = No
    PASSED -> ChangeDetector [REVISED]
ChangeDetector
    BLANK_AND_MISSING_DIFFER = No
    CHECK_COORDINATE_SYSTEMS = No
    CHECK_TYPES_AND_ENCODINGS = No
    LENIENT_MATCH = No
    MATCH = 2D
    MATCHATTRS = NUTS
    MATCH_STRATEGY = Match Selected Attributes
    PREEMPTIVE_ATTRS = FID
    UNCHANGED_OUTPUT = Output Original
    UPSERT_MODE = No
    UPDATED -> FeatureWriter [GISOZE.PROJEKT]
FeatureWriter
    DATASET = vyrokp_GISDVTB
    DATASET_ATTR = _dataset
    FEATURE_TYPE_LIST_ATTR = _feature_types
    FORMAT = ORACLE_SPATIAL
    ORACLE_SPATIAL_CHUNK_SIZE = 200
    ORACLE_SPATIAL_CONTAINS_MEASURES = NO
    ORACLE_SPATIAL_CREATE_SPATIAL_INDEX = no
    ORACLE_SPATIAL_DIMENSION = 2
    ORACLE_SPATIAL_GEOMETRY_COLUMN = GEOM
    ORACLE_SPATIAL_HANDLE_MULTIPLE_SPATIAL_COLUMNS = NO
    ORACLE_SPATIAL_INDEX_LEVELS = 0
    ORACLE_SPATIAL_NAMED_CONNECTION = vyrokp_GISDVTB
    ORACLE_SPATIAL_NONQUOTED_OBJECT_NAMES = Yes
    ORACLE_SPATIAL_NUMBER_OF_TILES = 8
    ORACLE_SPATIAL_PERSISTENT_CONNECTION = YES
    ORACLE_SPATIAL_SERVER_TYPE = ORACLE8i
    ORACLE_SPATIAL_SPATIAL_INDEX_MAXX = 180
    ORACLE_SPATIAL_SPATIAL_INDEX_MAXY = 90
    ORACLE_SPATIAL_SPATIAL_INDEX_MINX = -180
    ORACLE_SPATIAL_SPATIAL_INDEX_MINY = -90
    ORACLE_SPATIAL_START_TRANSACTION = 0
    ORACLE_SPATIAL_STRICT_ATTR_CONVERSION = No
    ORACLE_SPATIAL_TRANSACTION_INTERVAL = 1000
    TOTAL_FEATURES_WRITTEN_ATTR = _total_features_written

Bookmark: NUTS
Note: PostgreSQL
FeatureReader_3
    ATTRIBUTES = ruian.rn_obec_p,"fid,area,cleneni_sm_rozsah_kod,cleneni_sm_typ_kod,id_trans_ruian,kod,mluv_char_pad_2,mluv_char_pad_3,mluv_char_pad_4,mluv_char_pad_5,mluv_char_pad_6,mluv_char_pad_7,nazev,nespravny,nz_id_globalni,okres_kod,plati_od,pou_kod,status_kod,vlajka_obrazek,vlajka_text,zmena_grafiky,znak_obrazek,znak_text,puvod",ruian.rn_okres_p,"fid,area,id_trans_ruian,kod,kraj_1960_kod,nazev,nespravny,nuts_lau,nz_id_globalni,plati_od,vusc_kod,zmena_grafiky,puvod",ruian.rn_vusc_p,"fid,area,id_trans_ruian,kod,nazev,nespravny,nuts_lau,nz_id_globalni,plati_od,regsoudr_kod,zmena_grafiky,puvod"
    ATTR_ACCUM_MODE = Only Use Result
    COMBINE_GEOM = Use Result
    DATASET = cw00605pfmedb_fme_ruian
    FEATURETYPES = ruian.rn_obec_p ruian.rn_okres_p ruian.rn_vusc_p
    FORMAT = POSTGIS
    INTERACT = NONE
    OUTPUT_FEATURES_DISPLAY = Data Features
    POSTGIS_CREATE_FEATURE_TABLES_FROM_DATA = Yes
    POSTGIS_DISABLE_COLLECTION_SPLITTING = yes
    POSTGIS_FEATURES_PER_FETCH = 10000
    POSTGIS_NAMED_CONNECTION = cw00605pfmedb_fme_ruian
    POSTGIS_QUERY_FEATURE_TYPES_FOR_MERGE_FILTERS = Yes
    POSTGIS_READ_TIME_WITH_TIMEZONE = Yes
    POSTGIS_SCHEMAS_FOR_TABLE_LISTING = ruian
    POSTGIS_USE_SEARCH_ENVELOPE = NO
    POSTGIS_USE_TRUE_POSTGIS_TYPES = yes
    ruian.rn_okres_p -> AttributeManager_8
    ruian.rn_vusc_p -> AttributeFilter
AttributeManager_8
    ATTR_TABLE:
      REMOVE fid
      REMOVE area
      REMOVE id_trans_ruian
      REMOVE kod
      SET_TO NUTS = @Substring(@Value(nuts_lau),3)
      REMOVE kraj_1960_kod
      REMOVE nazev
      REMOVE nespravny
      REMOVE nz_id_globalni
      REMOVE plati_od
      REMOVE vusc_kod
      REMOVE zmena_grafiky
      REMOVE puvod
    -> AttributeRemover
AttributeFilter
    ATTR_NAME = kod
    ATTR_VALUES = <Empty>,<Missing>,<Null>,<Unfiltered>,19
    19 -> AttributeManager_2
AttributeManager_2
    ATTR_TABLE:
      REMOVE fid
      REMOVE area
      REMOVE id_trans_ruian
      REMOVE kod
      SET_TO NUTS = @Substring(@Value(nuts_lau),3)0
      REMOVE nazev
      REMOVE nespravny
      REMOVE nz_id_globalni
      REMOVE plati_od
      REMOVE zmena_grafiky
      REMOVE puvod
      REMOVE regsoudr_kod
    -> AttributeRemover
AttributeRemover
    REMOVE_ATTRS = nuts_lau
    -> SpatialFilter [Filter]
