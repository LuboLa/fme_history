FME workspace UPDATE_OBJ_VYR_from_OZ_PROJEKT.fmw

Parameters:
- SourceDataset_ORACLE_SPATIAL = vyrokp_GISOZETB   # Connection
- SourceDataset_ORACLE_SPATIAL_3 = vyrokp_GISDVTB   # Connection
- DestDataset_ORACLE_SPATIAL = vyrokp_GISDVTB   # Connection

Readers:
- ORACLE_SPATIAL_1: ORACLE_SPATIAL from $(SourceDataset_ORACLE_SPATIAL)
- ORACLE_SPATIAL_2: ORACLE_SPATIAL from $(SourceDataset_ORACLE_SPATIAL_3)

Writers:
- ORACLE_SPATIAL_3: ORACLE_SPATIAL to $(DestDataset_ORACLE_SPATIAL)

CIS_OBJEKT_VYROBY (reader ORACLE_SPATIAL_2)
    attributes: FID number(10,0), ORIENTATION number(6,3), Z number(20,8), QUALITY number(10,0), SHORT_VALUE varchar2(80), VALUE varchar2(1020), DATE_OF_CREATION date, ID_TYP_OBJ_VYR number(10,0), ID_ELEKTRARNA number(10,0), ID_OJ number(10,0), PSK_SUBFACILITY_CODE varchar2(40), NUTS number(3,0), ID_ACTIVE number(1,0), NUTS_CEZ varchar2(28), DOCMAN_CODE varchar2(40), ID number(10,0), SPP_CEZ varchar2(50), ID_STAV number(10,0), KOD_IS_VYROBA varchar2(80), ID_TIPOM number(10,0)
    -> TestFilter
TestFilter
    DEFAULT_VALUE = <UNFILTERED>
    PASSED_TEST_GROUP_OUTPUT = FIRST
    TEST_LIST = "BOOL_OP,OR,COMPOSITE_TEST,""""""1"""""",TEST_CLAUSE,TEST @Value(ID_TYP_OBJ_VYR) = 1",Uhelný zdroj el.,"BOOL_OP,OR,COMPOSITE_TEST,""""""1"""""",TEST_CLAUSE,TEST @Value(ID_TYP_OBJ_VYR) = 2",Jaderný zdroj el.,"BOOL_OP,OR,COMPOSITE_TEST,""""""1"""""",TEST_CLAUSE,TEST @Value(ID_TYP_OBJ_VYR) = 3",Paroplynový cyklus zdroj el.,"BOOL_OP,OR,COMPOSITE_TEST,""""""1"""""",TEST_CLAUSE,TEST @Value(ID_TYP_OBJ_VYR) = 4",Vodní zdroj el.,"BOOL_OP,OR,COMPOSITE_TEST,""""""1"""""",TEST_CLAUSE,TEST @Value(ID_TYP_OBJ_VYR) = 5",Větrný zdroj el.,"BOOL_OP,OR,COMPOSITE_TEST,""""""1"""""",TEST_CLAUSE,TEST @Value(ID_TYP_OBJ_VYR) = 6",Fotovoltaický zdroj el.,"BOOL_OP,OR,COMPOSITE_TEST,""""""1"""""",TEST_CLAUSE,TEST @Value(ID_TYP_OBJ_VYR) = 7",Kogenerační jednotka,"BOOL_OP,OR,COMPOSITE_TEST,""""""1"""""",TEST_CLAUSE,TEST @Value(ID_TYP_OBJ_VYR) = 8",Bateriové úložiště el.,"BOOL_OP,OR,COMPOSITE_TEST,""""""1"""""",TEST_CLAUSE,TEST @Value(ID_TYP_OBJ_VYR) = 9",Bioplynový zdroj el.,"BOOL_OP,OR,COMPOSITE_TEST,""""""1"""""",TEST_CLAUSE,TEST @Value(ID_TYP_OBJ_VYR) = 10",Výtopna,"BOOL_OP,OR,COMPOSITE_TEST,""""""1"""""",TEST_CLAUSE,TEST @Value(ID_TYP_OBJ_VYR) = 11",ZEVO,"BOOL_OP,OR,COMPOSITE_TEST,""""""1"""""",TEST_CLAUSE,TEST @Value(ID_TYP_OBJ_VYR) = 12",Plynový zdroj el.,"BOOL_OP,OR,COMPOSITE_TEST,""""""1"""""",TEST_CLAUSE,TEST @Value(ID_TYP_OBJ_VYR) = 13",Trafostanice,"BOOL_OP,OR,COMPOSITE_TEST,""""""1"""""",TEST_CLAUSE,TEST @Value(ID_TYP_OBJ_VYR) = 14",Centrála společnosti HS,"BOOL_OP,OR,COMPOSITE_TEST,""""""1"""""",TEST_CLAUSE,TEST @Value(ID_TYP_OBJ_VYR) = 15",Energetické produkty,"BOOL_OP,OR,COMPOSITE_TEST,""""""1"""""",TEST_CLAUSE,TEST @Value(ID_TYP_OBJ_VYR) = 16",Rozvodna
    Větrný zdroj el. -> AttributeManager_4
    Fotovoltaický zdroj el. -> AttributeManager_4
    Trafostanice -> AttributeManager_4
AttributeManager_4
    -> FeatureJoiner [LEFT]
    -> ChangeDetector [ORIGINAL]
OZ_PROJEKT (reader ORACLE_SPATIAL_1)
    attributes: AREA number(20,8), DATUM_PODANI_ZMENY_UP date, DATUM_PREDANI_KONTROLA date, DATUM_PREDANI_ODB_ROZVOJE date, DATUM_PROJED_ZASTUPIT date, DATUM_SCHAV_PROJ date, DATUM_SITE_VISIT date, DATUM_UPRAV date, DATUM_VYRAZENI date, DATUM_VYTVOR date, DATUM_ZMENY_UP date, DELKA_PRIPOJ number(10,2), FAZE_CLARITY varchar2(20), FID number(10,0), FID_BOD_PRIPOJENI number(10,0), FID_OOCOZ number(10,0), FID_PRIPOJENI number(10,0), FID_PRIPRAVAR_PROJ number(10,0), FID_PROJEKT_MANAGER number(10,0), GEOM_CENTER_POINT_WKT varchar2(200), GPS_BOD_PRIPOJENI_CLARITY varchar2(200), ID_ACCESS number(10,0), ID_BROWNFIELD number(10,0), ID_CLARITY varchar2(40), ID_DIST_UZEMI number(10,0), ID_DOT_TITUL number(10,0), ID_DRUH number(10,0), ID_DRUH_KOMUNIT_PODPORY number(10,0), ID_DRUH_PROJEKTU_OZE number(10,0), ID_DUVOD_VYRAZENI number(10,0),
      ID_EIA number(10,0), ID_H67 number(10,0), ID_CHRANENE_UZEMI number(10,0), ID_KOMUN_PROJEKT number(10,0), ID_KRAJ_RAZ number(10,0), ID_ORIENT_POZEMKU number(10,0), ID_PRIORITA number(10,0), ID_PRIP_OVER number(10,0), ID_REKULTIVACE number(10,0), ID_REZIM number(10,0), ID_SEIA number(10,0), ID_SKLONITOST_POZEM number(10,0), ID_SOULAD_UPD number(10,0), ID_STAV number(10,0), ID_TYP number(10,0), ID_UP number(10,0), ID_VB number(10,0), ID_ZAJIST_POZEMKU number(10,0), ID_ZPF number(10,0), JEDN_NAJEM_HA number(10,2), KATUZ_KOD number(10,0), KATUZ_NAZEV varchar2(200), LEX_OZE_CLARITY varchar2(10), NAJEM_FAZE_ODSTR_MENA number(10,0), NAZEV varchar2(1020), NUTS_FVE varchar2(32), OBEC_KOD number(10,0), OBEC_NAZEV varchar2(200), OKRES_KOD number(10,0), OKRES_NAZEV varchar2(200),
      OLD_FID number(10,0), PLOCHA number(10,3), PLOCHA_CELKEM number(10,3), PORAD_CISLO number(10,0), POZEMEK_NAKUP_HA number(8,4), POZEMEK_NAKUP_MENA number(10,2), POZNAMKA varchar2(4000), PRIPRAVAR_PROJ_CLARITY varchar2(100), PROJ_MANAGER_CLARITY varchar2(50), PROVEDENI_COMPLIANCE number(10,0), REZERVA number(1,0), REZERVACE_NAJEM_1 number(10,2), REZERVACE_NAJEM_2 number(10,2), SMLOVA_PRIPOJ varchar2(1020), SPP_PRVEK varchar2(1020), SPP_PRVEK_CEZ_CLARITY varchar2(50), STAV_CLARITY varchar2(80), STAV_URAD_KOD number(10,0), STAV_URAD_NAZEV varchar2(1020), STAVBA_NAJEM number(10,2), USER_UPRAV varchar2(1020), USER_VYTVOR varchar2(1020), VUSC_KOD number(10,0), VUSC_NAZEV varchar2(200), VYKON number(10,3), VYKON_INSTALOVANY number(10,2), VYKON_ZTRACENY number(10,2), VYNETI_ZPF number(10,2), VYSE_KOMUNIT_PODPORY number(10,3), ZSJ_KOD number(10,0),
      ZSJ_NAZEV varchar2(200)
    -> Tester
Note: Kontrola zadání Druhu projektu OZE
Tester
    BOOL_OP = OR
    TEST_CLAUSE = TEST ID_DRUH_PROJEKTU_OZE ATTRIBUTE_HAS_A_VALUE ""
    TEST_MODE = TEST
    PASSED -> StringPadder
StringPadder
    BLANK_ATTRIBUTE = Yes
    PADCHAR = 0
    SIDE = Left
    SRC_ATTRS = OLD_FID
    WIDTH = 5
    -> AttributeManager
AttributeManager
    ATTR_TABLE = SET_TO SHORT_VALUE (varchar(200)) = FME_CONDITIONAL:DEFAULT_VALUE'@Value(OLD_FID)'BOOL_OP;OR;COMPOSITE_TEST;1;TEST @Value(ID_DRUH_PROJEKTU_OZE) = 1'FV@Value(OLD_FID)'BOOL_OP;OR;COMPOSITE_TEST;1;TEST @Value(ID_DRUH_PROJEKTU_OZE) = 2'TR@Value(OLD_FID)'BOOL_OP;OR;COMPOSITE_TEST;1;TEST @Value(ID_DRUH_PROJEKTU_OZE) = 3'VT@Value(OLD_FID)'FME_NUM_CONDITIONS4___
    -> CenterPointReplacer
CenterPointReplacer
    POINTTYPE = CENTEROFGRAV
    POINT -> AttributeValueMapper
    UNTOUCHED -> AttributeValueMapper
Note: ID TYP OBJ VYR
AttributeValueMapper
    LUT = 3,5,1,6,2,13
    MAPPING_DIRECTION = FORWARD
    SRC = ID_DRUH_PROJEKTU_OZE
    VAL_ATTR = ID_TYP_OBJ_VYR
    -> AttributeManager_3
AttributeManager_3
    ATTR_TABLE:
      RENAME_SET_VALUE NAZEV > VALUE (varchar(1020))
      REMOVE OLD_FID (int64)
      REMOVE ID_DRUH_PROJEKTU_OZE (int64)
      REMOVE fme_rejection_code (buffer)
      SET_TO ID_STAV (uint64) = 2
    -> FeatureJoiner [RIGHT]
FeatureJoiner
    ATTR_CONFLICT_RES = Prefer Right
    GEOMETRY_HANDLING = Prefer Left
    JOIN_KEYS = SHORT_VALUE SHORT_VALUE AUTO
    JOIN_MODE = Inner
    JOINED -> ChangeDetector [REVISED]
    UNJOINED_RIGHT -> ChangeDetector [REVISED]
ChangeDetector
    BLANK_AND_MISSING_DIFFER = No
    CHECK_TYPES_AND_ENCODINGS = No
    MATCHATTRS = ID_STAV ID_TYP_OBJ_VYR VALUE FID
    MATCH_STRATEGY = Match Selected Attributes
    PREEMPTIVE_ATTRS = SHORT_VALUE
    UNCHANGED_OUTPUT = Output Original
    UPSERT_MODE = No
    UPDATED -> CIS_OBJEKT_VYROBY (writer ORACLE_SPATIAL_3)
    INSERTED -> CIS_OBJEKT_VYROBY (writer ORACLE_SPATIAL_3)
CIS_OBJEKT_VYROBY (writer ORACLE_SPATIAL_3)
    attributes: FID number(10,0), SHORT_VALUE varchar2(80), VALUE varchar2(1020), ID_TYP_OBJ_VYR number(10,0), ID_STAV number(10,0)
