FME workspace 1_Kontrola_dokumentace_Upsert_seznam_slozek.fmw

Parameters:
- Export_check = Ne   # Chcete exportovat Výpis stavu těžby souborů?
- Import_check = Ano   # Chcete nahrát novou složku ke zpracování?
- Relativni_cesta = ETU\ETU_0973_JMA   # Zadejte složku se soubory k těžbe: (ETU/JMA_1234_ETU)
- Retry_check = Opakovat   # zadání" Chcete-li opakovat těžbu již vložené složky se soubory, zaškrtněte "Opakovat"
- Absolutni_cesta = \\dfs03.cezdata.corp\CEZ\DKE\9050060_ŘTKE\TPKE\RIZEK\JMA do DOCMAN\   # Absolutni cesta/Absolute path
- DB_PG_DOKE = PG_DOKE   # PG_DOKE
- FME_SERVER_RUNTIME_USER = zdeborjan   # FME Flow Runtime User

Creator
    GEOMTYPE = Geometry Object
    NUM = 1
    CREATED -> TestFilter
TestFilter
    DEFAULT_VALUE = <UNFILTERED>
    PASSED_TEST_GROUP_OUTPUT = FIRST
    TEST_LIST:
      "BOOL_OP,AND,COMPOSITE_TEST,""""""1 AND 2"""""",TEST_CLAUSE,TEST $(Import_check) = Ano
      TEST $(Export_check) = Ano",Export a Import,"BOOL_OP,OR,COMPOSITE_TEST,""""""1"""""",TEST_CLAUSE,TEST $(Export_check) = Ano",Export ,"BOOL_OP,OR,COMPOSITE_TEST,""""""1"""""",TEST_CLAUSE,TEST $(Import_check) = Ano",Import
    Export a Import -> AttributeManager
    Export a Import -> SQLExecutor [INITIATOR]
    Export -> SQLExecutor [INITIATOR]
    Import -> AttributeManager

Bookmark: Upsert tabulky seznam_slozek
Note: Dle Retry_check se nastavuje hodnota "status"
AttributeManager
    ATTR_TABLE:
      REMOVE _creation_instance (uint64)
      SET_TO plant_type (varchar(200))
      SET_TO main_folder_name (varchar(200)) = @SubstringRegularExpression($(Relativni_cesta),[^\\]+$,0,0,0,caseSensitive=TRUE)
      SET_TO short_folder_path (varchar(200)) = $(Relativni_cesta)
      SET_TO nuts_jma_number (varchar(200)) = @SubstringRegularExpression(@Value(main_folder_name),[0-9]{4},0,0,0,caseSensitive=TRUE)
      SET_TO status (uint64) = 000
      SET_TO plant_short_name (varchar(200))
    -> FileExistenceChecker
FileExistenceChecker
    Input = $(Absolutni_cesta)\@Value(short_folder_path)
    Exists -> TestFilter_2
    DoesNotExist -> Email_body
TestFilter_2
    DEFAULT_VALUE = <UNFILTERED>
    PASSED_TEST_GROUP_OUTPUT = FIRST
    TEST_LIST = "BOOL_OP,OR,COMPOSITE_TEST,""""""1"""""",TEST_CLAUSE,CASE_INSENSITIVE_TEST @Value(main_folder_name) CONTAINS_REGEX ^FV|^TR|^VT",OZE,"BOOL_OP,OR,COMPOSITE_TEST,""""""1"""""",TEST_CLAUSE,CASE_SENSITIVE_TEST @Value(main_folder_name) CONTAINS_REGEX ^(ETU|ELE|EGT|EPR|PPC)_[0-9]{4}_JMA",KE JMA
    KE JMA -> AttributeManager_2
AttributeManager_2
    ATTR_TABLE:
      SET_TO plant_type (varchar(200)) = KE
      SET_TO plant_short_name (varchar(200)) = @Substring(@Value(main_folder_name),0,3)
    USER_EXPOSED_ATTRIBUTES = plant_type,main_folder_name,short_folder_path,status,nuts_jma_number
    -> ChangeDetector [REVISED]
SQLCreator
    DATASET = PG_DOKE
    EXPOSED_ATTRIBUTE_LIST = id,main_folder_name,short_folder_path,status,plant_type,plant_short_name
    FORMAT = POSTGRES
    OUTPUT_FEATURES_DISPLAY = Data Features
    POSTGRES_CREATE_FEATURE_TABLES_FROM_DATA = Yes
    POSTGRES_NAMED_CONNECTION = PG_DOKE
    POSTGRES_QUERY_FEATURE_TYPES_FOR_MERGE_FILTERS = Yes
    POSTGRES_READ_TIME_WITH_TIMEZONE = Yes
    POSTGRES_SCHEMAS_FOR_TABLE_LISTING = tezba
    SQL_STATEMENT:
      SELECT * FROM tezba."seznam_slozek"
      ORDER BY id ASC
    RESULT -> ChangeDetector [ORIGINAL]
ChangeDetector
    BLANK_AND_MISSING_DIFFER = No
    CHECK_TYPES_AND_ENCODINGS = No
    MATCHATTRS = status
    MATCH_STRATEGY = Match Selected Attributes
    ORIGINAL_ATTRIBUTES = id
    PREEMPTIVE_ATTRS = main_folder_name
    UNCHANGED_OUTPUT = Output Revised
    UPSERT_MODE = No
    UPDATED -> Tester
    INSERTED -> FeatureWriter_2 [Output]
Tester
    BOOL_OP = OR
    TEST_CLAUSE = TEST $(Retry_check) = Opakovat
    TEST_MODE = TEST
    PASSED -> FeatureWriter_2 [Output]
    FAILED -> Email_body_2
FeatureWriter_2
    DATASET = $(DB_PG_DOKE)
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = No
    POSTGRES_NAMED_CONNECTION = $(DB_PG_DOKE)
    POSTGRES_START_TRANSACTION = 0
    POSTGRES_STRICT_TEMPORAL_TYPE_HANDLING = Yes
    POSTGRES_TRANSACTION_INTERVAL = 1000
    TOTAL_FEATURES_WRITTEN_ATTR = _total_features_written
    SUMMARY -> Email_body_3

Bookmark: Emailové netifikace
Note: Notifikovat o nesprávnosti složky
Email_body: AttributeManager
    ATTR_TABLE:
      SET_TO Email_body_FME (varchar(200)) = Zadaná složka "$(Relativni_cesta)" (Celá cesta:"$(Absolutni_cesta)\$(Relativni_cesta)") nenalezena. Složka nebyla přidána do pořadníku ke kontrole.
      SET_TO Email_subject_FME (buffer) = Chyba
      REMOVE plant_type (varchar(200))
      REMOVE main_folder_name (varchar(200))
      REMOVE short_folder_path (varchar(200))
      REMOVE nuts_jma_number (varchar(200))
      REMOVE status (uint64)
      REMOVE plant_short_name (varchar(200))
    -> HTTPCaller
Note: Notifikace u nenahrání z důvodu již narané složký z dřívějška
Email_body_2: AttributeManager
    ATTR_TABLE:
      SET_TO Email_body_FME (varchar(200)) = Zadaná složka "$(Relativni_cesta)" (Celá cesta:"$(Absolutni_cesta)\$(Relativni_cesta)") nebyla přidána, protože v pořadníku již existuje. Pokud chcete kontrolu opakovat, zaškrtněte v úvodním formuláři "Opakovat".
      SET_TO Email_subject_FME (buffer) = Upozornění
      REMOVE plant_type (varchar(200))
      REMOVE main_folder_name (varchar(200))
      REMOVE short_folder_path (varchar(200))
      REMOVE nuts_jma_number (varchar(200))
      REMOVE status (uint64)
      REMOVE plant_short_name (varchar(200))
      REMOVE id (buffer)
      REMOVE fme_db_operation (char(9))
    -> HTTPCaller
Email_body_3: AttributeManager
    ATTR_TABLE:
      SET_TO Email_body_FME (varchar(200)) = Zadaná složka "$(Relativni_cesta)" (Celá cesta:"$(Absolutni_cesta)\$(Relativni_cesta)") byla úspešně přidána do pořadníku ke zpracování.
      SET_TO Email_subject_FME (buffer) = Upozornění
      REMOVE _feature_types{}.count (uint64)
      REMOVE _feature_types{}.name (buffer)
      REMOVE _dataset (buffer)
      REMOVE _total_features_written (uint64)
    -> HTTPCaller
HTTPCaller
    ADDITIONAL_URL_PARAMETERS = KPJM;$(FME_SERVER_RUNTIME_USER)
    AUTH_METHOD = Basic
    AUTH_PASSWORD =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
    AUTH_USERNAME = qpfmeserver
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://restapidv2.cezdata.corp/ad/v1/user
    TRANSFER_TIMEOUT_LENGTH = 90
    USE_COOKIES = No
    VERIFY_SSL_CERTIFICATES = Yes
    -> JSONExtractor
JSONExtractor
    EXTRACT_QUERY_TABLE = Email_FME json[*]["email"]
    FILEPATH_OR_URL = $(FME_MF_DIR)new 8.json
    READ_FROM_FILE = YES
    EVALUATED -> FMEServerEmailGenerator
FMEServerEmailGenerator
    email_from = FME Flow
    email_subject = @Value(Email_subject_FME)
    email_subscriber_content = @Value(Email_body_FME)
    email_to = @Value(Email_FME)
    -> FMEServerNotifier
FMEServerNotifier
    BODY = @Value(text_line_data)
    PASSWORD =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
    SERVER_NAME = https://fme:443
    TOPIC = FME-EDP
    USERNAME = EDP_APP

Bookmark: Generování výstupního souboru
SQLExecutor
    COMBINE_ATTRS = Result Attributes Only
    COMBINE_GEOM = Initiator Geometry Only
    DATASET = $(DB_PG_DOKE)
    EXPOSED_ATTRIBUTE_LIST = short_folder_path,status
    FORMAT = POSTGRES
    OUTPUT_FEATURES_DISPLAY = Data Features
    POSTGRES_CREATE_FEATURE_TABLES_FROM_DATA = Yes
    POSTGRES_NAMED_CONNECTION = $(DB_PG_DOKE)
    POSTGRES_QUERY_FEATURE_TYPES_FOR_MERGE_FILTERS = Yes
    POSTGRES_READ_TIME_WITH_TIMEZONE = Yes
    POSTGRES_SCHEMAS_FOR_TABLE_LISTING = tezba
    SQL_STATEMENT:
      Select short_folder_path,
              status
      from "tezba"."seznam_slozek"
      order by id
    RESULT -> AttributeValueMapper
Note: Status kódy - vylepšit
AttributeValueMapper
    DEFAULT_VALUE = 999
    LUT = 000,Připraveno,100,Spuštěno
    MAPPING_DIRECTION = FORWARD
    SRC = status
    VAL_ATTR = Status_FME
    -> AttributeManager_3
AttributeManager_3
    ATTR_TABLE:
      SET_TO Složka ke zpracování (varchar(200)) = $(Absolutni_cesta)\@Value(short_folder_path)
      RENAME_SET_VALUE Status_FME > Status zpracování (buffer)
      REMOVE short_folder_path (buffer)
      REMOVE status (varchar(50))
    -> FeatureWriter [Output]
FeatureWriter
    DATASET = Vypis_cest_ke_zpracovani.xlsx
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = Yes
    XLSXW_FIELD_NAMES_FORMATTING = Yes
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TRUNCATE_TABLE = Yes
    XLSXW_WRITER_MODE = Insert

FME custom transformer FMEServerEmailGenerator
Description
This transformer provides an easy method for creating an email message to be sent by the FME Server Notification Service.
Input Ports
Input
This transformer will accept any feature.
Output Ports
Output
Features are output with text_line_data attribute required for the Text File Writer (see Usage Notes).
text_line_data: Contains JSON-formatted message that is required by the Email Subscription (see Usage Notes).
<Rejected>
Features will be rejected if the 'To:' field does not contain a valid email address in the form email@domain. Rejected features are output with value INVALID_PARAMETER stored in the fme_rejection_code attribute.
Parameters
To
Email address for To: field. 
Cc
Email address for Cc: field.
Bcc
Email address for Bcc: field.
From
Email address for From: field.
Reply to
Email address for Reply to: field.
Subject
Text string for subject of email.
Content
The main body of the email message.
Attachments
List of files to attach to email. For multiple files, separate filenames with a comma (e.g. file1.txt,file2.txt). File paths and features stored as attributes are both accepted.
Note: Attachments may not process if not accessible by FME Server.  
Usage Notes
Step 1. Create Topic and Email Subscription
In the FME Server Web UI, create a Topic for notifications to be sent to, and also create an Email Subscription that subscribes to this Topic.
Step 2. Create a Workspace
Once you fill out the the required paramerts for this transformer, you can send the email message in two different ways:
A. Send an email when the workspace completes:  
Add a Text File Writer to the workspace  
Connect FMEServerEmailGenerator Output to the Text File Writer  
Publish the workspace to FME Server
Register it with the Job Submitter, and/or Data Download, and/or Notification Service  
For each service, click the edit button  
Expand the Notify on Job Completion section
For Topics to Publish (Success), select the Topic created in Step 1  
For the Post Data parameter, select the Text File Writer added to the workspace  
Finish publishing the workspace  
Now the workspace will send an email whenever it is run through the FME Server Service you registered it with  
B. Send an email using a transformer:  
Add an FMEServerNotifier transformer to your workflow  
Configure it to publish to the Topic that you created earlier  
For Content, select the text_line_data attribute  
Now the workspace will send an email whenever it is run

Parameters:
- email_to =   # To
- email_cc =   # Cc
- email_bcc =   # Bcc
- email_from =   # From
- email_replyto =   # Reply to
- email_subject =   # Subject
- email_subscriber_content =   # Content
- email_attachment_paths =   # Attachments

Input (input)
    -> Counter
Tester_2_FAILED: Junction
    -> AttributeCreator_3
Note: Rejected
AttributeCreator_3: Junction
    -> AttributeCreator_2
AttributeCreator_2
    ATTR_TABLE = SET_TO fme_rejection_code = INVALID_PARAMETER
    -> <Rejected> (output)
<Rejected> (output)
JSONTemplater_2_ROOT: Junction
    -> JSONTemplater_2 [ROOT]
Note: No attachment
Output_2: Junction
    -> AttributeKeeper
AttributeKeeper
    CREATE_BULK_MODE_FEATURES = No
    KEEP_ATTRS = text_line_data
    -> Output (output)
Output (output)

Bookmark: Parse for attachement
Counter
    CNT_ATTR = _email_feature_id
    DOMAIN = counter
    SCOPE = Local
    START = 0
    -> ParameterFetcher
ParameterFetcher
    ATTR_LIST = _email_from $(email_from) _email_replyto $(email_replyto) _email_attachment_paths $(email_attachment_paths) _email_cc $(email_cc) _email_bcc $(email_bcc)
    -> AttributeCreator
AttributeCreator
    ATTR_TABLE:
      SET_TO _email_to = $(email_to)
      SET_TO _email_subject = $(email_subject)
      SET_TO _email_subscriber_content = $(email_subscriber_content)
    -> Tester_2
Note: Test that To field contains / valid email address
Note: Reject
Tester_2
    BOOL_OP = OR
    TEST_CLAUSE = TEST @Value(_email_to) CONTAINS @
    TEST_MODE = TEST
    PASSED -> Tester_3
    FAILED -> Tester_2_FAILED

Bookmark: Multiple attachment string wizardy
Tester_3
    BOOL_OP = OR
    TEST_CLAUSE = TEST @Value(_email_attachment_paths) CONTAINS " "
    TEST_MODE = TEST
    PASSED -> SubstringExtractor
    FAILED -> Tester_3_FAILED
SubstringExtractor
    END = -2
    RESULT_ATTR = _email_attachment_paths
    SRC_STRING = @Value(_email_attachment_paths)
    START = 1
    -> StringReplacer_3
StringReplacer_3
    CASE = NO
    FIND_TEXT = " "
    NO_MATCH = _FME_NO_OP_
    REGEXP = NO
    REPLACE_TEXT = "" ""
    SRC_ATTRS = _email_attachment_paths
    -> JSONTemplater [ROOT]
Note: Single attachment
Tester_3_FAILED: Junction
    -> JSONTemplater_2_ROOT

Bookmark: Add multiple attachments
JSONTemplater
    RESULT_ATTRIBUTE = text_line_data
    ROOT_QUERY_EXPR:
      {
      "email_to": fme:get-attribute("_email_to"),
      "email_cc": fme:get-attribute("_email_cc"),
      "email_bcc": fme:get-attribute("_email_bcc"),
      "email_from": fme:get-attribute("_email_from"),
      "email_replyto": fme:get-attribute("_email_replyto"),
      "email_subject": string(fme:get-attribute("_email_subject")),
      "subscriber_content": string(fme:get-attribute("_email_subscriber_content"))
      }
    VISIBLE_QUERY_VALIDATE = Yes
    -> Tester
Tester
    BOOL_OP = OR
    TEST_CLAUSE = TEST _email_attachment_paths ATTRIBUTE_IS_EMPTY ""
    TEST_MODE = TEST
    PASSED -> Tester_PASSED
    FAILED -> AttributeSplitter_2
AttributeSplitter_2
    ATTR_NAME = _email_attachment_paths
    DELIMITER = " "
    DROP_EMPTY_PARTS = No
    LIST_NAME = _email_attachment_path_list
    TRIM_OPTION = Both
    -> ListExploder_2
ListExploder_2
    ATTR_ACCUM_MODE = Merge List Attributes
    ATTR_CONFLICT_RES = Use List Attribute Values
    INDEX_ATTR = _element_index
    LIST_ATTR = _email_attachment_path_list{}
    ELEMENTS -> StringConcatenator_2
StringConcatenator_2
    ACTION = Create New Attribute
    PARM_LINE = "email_attachment{@Value(_element_index)}":@Value(_email_attachment_path_list)
    VAL_ATTR = _email_attachment_json
    -> Aggregator_2
Aggregator_2
    ACCUM_ATTRS_NAME = Merge Incoming Attributes
    AGGREGATE_TYPE = Homogeneous Collection (If Possible)
    CONCAT_ATTRS = _email_attachment_json
    GROUP_BY = _email_feature_id
    MODE = Geometry - Assemble One Level
    SEP = ,
    AGGREGATE -> StringReplacer_5
StringReplacer_5
    CASE = NO
    FIND_TEXT = \
    NO_MATCH = _FME_NO_OP_
    REGEXP = NO
    REPLACE_TEXT = \\
    SRC_ATTRS = _email_attachment_json
    -> StringReplacer_4
StringReplacer_4
    CASE = NO
    FIND_TEXT = }
    NO_MATCH = _FME_NO_OP_
    REGEXP = NO
    REPLACE_TEXT = , @Value(_email_attachment_json)}
    SRC_ATTRS = text_line_data
    -> AttributeKeeper
Note: No attachment
Tester_PASSED: Junction
    -> Output_2

Bookmark: Add single attachment
JSONTemplater_2
    RESULT_ATTRIBUTE = text_line_data
    ROOT_QUERY_EXPR:
      {
      "email_to": fme:get-attribute("_email_to"),
      "email_cc": fme:get-attribute("_email_cc"),
      "email_bcc": fme:get-attribute("_email_bcc"),
      "email_from": fme:get-attribute("_email_from"),
      "email_replyto": fme:get-attribute("_email_replyto"),
      "email_subject": string(fme:get-attribute("_email_subject")),
      "subscriber_content": string(fme:get-attribute("_email_subscriber_content"))
      }
    VISIBLE_QUERY_VALIDATE = Yes
    -> Tester_4
Tester_4
    BOOL_OP = OR
    TEST_CLAUSE = TEST _email_attachment_paths ATTRIBUTE_IS_EMPTY ""
    TEST_MODE = TEST
    PASSED -> Tester_PASSED_2
    FAILED -> AttributeSplitter
AttributeSplitter
    ATTR_NAME = _email_attachment_paths
    DELIMITER = " "
    DROP_EMPTY_PARTS = No
    LIST_NAME = _email_attachment_path_list
    TRIM_OPTION = Both
    -> ListExploder
ListExploder
    ATTR_ACCUM_MODE = Merge List Attributes
    ATTR_CONFLICT_RES = Use List Attribute Values
    INDEX_ATTR = _element_index
    LIST_ATTR = _email_attachment_path_list{}
    ELEMENTS -> StringConcatenator
StringConcatenator
    ACTION = Create New Attribute
    PARM_LINE = "email_attachment{@Value(_element_index)}":"@Value(_email_attachment_path_list)"
    VAL_ATTR = _email_attachment_json
    -> Aggregator
Aggregator
    ACCUM_ATTRS_NAME = Merge Incoming Attributes
    AGGREGATE_TYPE = Homogeneous Collection (If Possible)
    CONCAT_ATTRS = _email_attachment_json
    GROUP_BY = _email_feature_id
    MODE = Geometry - Assemble One Level
    SEP = ,
    AGGREGATE -> StringReplacer_2
StringReplacer_2
    CASE = NO
    FIND_TEXT = \
    NO_MATCH = _FME_NO_OP_
    REGEXP = NO
    REPLACE_TEXT = \\
    SRC_ATTRS = _email_attachment_json
    -> StringReplacer
StringReplacer
    CASE = NO
    FIND_TEXT = }
    NO_MATCH = _FME_NO_OP_
    REGEXP = NO
    REPLACE_TEXT = , @Value(_email_attachment_json)}
    SRC_ATTRS = text_line_data
    -> AttributeKeeper
Note: No attachment
Tester_PASSED_2: Junction
    -> Output_2

FME custom transformer FileExistenceChecker
Description
This transformer checks if input file paths exist and routes features accordingly.
The transformer supports UNC path, Zip files(*.zip) and wildcards. 
Details
The transformer will check if the filename selected in InputPort exists or not. 
The path can be supplied from a parameter, a network share location, by selecting a filename or using wildcards. 
Notes
Multiple filenames are not supported
Path to file must exist (no missing folders in the path)
FTP paths are not supported
Input
Filename path to check if file exists.   
Parameters
Input ports
Input File Path: Full path to the file to check for existence.  
Output Ports
Exists:Features are output through this port if the file exists.   
_path: The attribute stores the path to the file.  
DoesNotExist:Features are output through this port if the file does not exists.   
_path: This attribute stores the path to the file.

Parameters:
- Input =   # Input File Path

Input (input)
    -> ParameterFetcher
ParameterFetcher
    ATTR_LIST = FEC_FullPath {$(Input)}
    -> PythonCaller
AttributeManager
    ATTR_TABLE:
      REMOVE FEC_exists
      REMOVE FEC_FullPath
    -> Exists (output)
Exists (output)
AttributeManager_2
    ATTR_TABLE:
      REMOVE FEC_exists
      REMOVE FEC_FullPath
    -> DoesNotExist (output)
DoesNotExist (output)

Bookmark: Check if File Exists
PythonCaller
    NEW_ATTRIBUTES = FEC_exists
    PYTHONSOURCE:
      import fmeobjects
      import glob
      import zipfile

      def processFeature(feature):

          # Get input path attribute
          fullpath=feature.getAttribute("FEC_FullPath")

          # Check if the file exists
          if glob.glob(fullpath):
              feature.setAttribute("FEC_exists","Yes")
              # if not, try checking inside a zip file
          else:
              fullpath = fullpath.replace("\\","/")
              idx = fullpath.find(".zip")
              if idx > -1:
                  zipPath = fullpath[:idx+4]
                  pathInZip = fullpath[idx+5:]    #i.e. .zip/
                  try:
                      with zipfile.ZipFile(zipPath, 'r') as f:
                          if isinstance(f.getinfo(pathInZip),zipfile.ZipInfo):
                              feature.setAttribute("FEC_exists","Yes")
                              return
                  except (KeyError, FileNotFoundError) as e:
                      pass
                  # not found in a zipfile or in filesystem - does not exist
                  feature.setAttribute("FEC_exists","No")
    PYTHONSYMBOL = processFeature
    -> Tester
Tester
    BOOL_OP = OR
    TEST_CLAUSE = TEST @Value(FEC_exists) = Yes
    TEST_MODE = TEST
    PASSED -> AttributeManager
    FAILED -> AttributeManager_2
