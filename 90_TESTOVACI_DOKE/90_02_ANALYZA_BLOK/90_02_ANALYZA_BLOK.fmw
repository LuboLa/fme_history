FME workspace 90_02_ANALYZA_BLOK.fmw

Parameters:
- ID = 233

FeatureReader_2
    ATTR_ACCUM_MODE = Only Use Result
    COMBINE_GEOM = Use Result
    INTERACT = <No Spatial Filter>
    ORDER_RESULTS = No
    OUTPUT_FEATURES_DISPLAY = Schema and Data Features

Bookmark: BLOKY A ATRIBUTY
Note: Status = 3
SQLCreator
    DATASET = PG_DOKE
    EXPOSED_ATTRIBUTE_LIST = path_directory_windows,path_rootname,path_extension
    FORMAT = POSTGRES
    OUTPUT_FEATURES_DISPLAY = Data Features
    POSTGRES_CREATE_FEATURE_TABLES_FROM_DATA = Yes
    POSTGRES_NAMED_CONNECTION = PG_DOKE
    POSTGRES_QUERY_FEATURE_TYPES_FOR_MERGE_FILTERS = Yes
    POSTGRES_READ_TIME_WITH_TIMEZONE = Yes
    POSTGRES_SCHEMAS_FOR_TABLE_LISTING = tezba
    SQL_STATEMENT:
      Update tezba."Seznam_souboru"
      set "Status" = 3
      where "ID" = $(ID)
      returning "path_directory_windows", "path_rootname", "path_extension"
    RESULT -> FeatureReader [INITIATOR]
Note: Načte dwg nerozložené
FeatureReader
    ATTR_ACCUM_MODE = Only Use Result
    AUTOCAD_OD_ALL_MERGED_FILTERS_NEED_NO_DEFS = Yes
    AUTOCAD_OD_APPLY_WORLD_FILE = no
    AUTOCAD_OD_CONVERT_ZERO_LENGTH_ARCS_TO_POINTS = no
    AUTOCAD_OD_EVALUATE_MLINE_GEOM = no
    AUTOCAD_OD_EXPLODE_MTEXT = no
    AUTOCAD_OD_IGNORE_FROZEN_LAYERS = yes
    AUTOCAD_OD_IGNORE_HIDDEN_LAYERS = no
    AUTOCAD_OD_IGNORE_LOCKED_LAYERS = no
    AUTOCAD_OD_IGNORE_UCS = no
    AUTOCAD_OD_IGNORE_VIEWPORT_FROZEN_LAYERS = yes
    AUTOCAD_OD_INTERPRET_EXTENDED_DATA = no
    AUTOCAD_OD_LIST_ATTRIBUTE_ENTITY_DATA = no
    AUTOCAD_OD_LIST_EXTENDED_DATA = no
    AUTOCAD_OD_OD_READ_MODE = od_mode_entity
    AUTOCAD_OD_PRESERVE_CLIPPED_RASTERS = no
    AUTOCAD_OD_PRESERVE_COMPLEX_HATCHES = no
    AUTOCAD_OD_QUALIFY_OBJECT_DATA_RECORDS_WITH_TABLE_NAME = no
    AUTOCAD_OD_QUERY_FEATURE_TYPES_FOR_MERGE_FILTERS = Yes
    AUTOCAD_OD_READ_AS_2_5D = no
    AUTOCAD_OD_READ_GROUPS = no
    AUTOCAD_OD_READ_MODEL_SPACE = yes
    AUTOCAD_OD_READ_PAPER_SPACE = NO
    AUTOCAD_OD_READ_PROXY_GRAPHICS = yes
    AUTOCAD_OD_READ_RASTERS = no
    AUTOCAD_OD_READ_REGIONS_AS_AREAS = yes
    AUTOCAD_OD_READ_SYS_VARS = no
    AUTOCAD_OD_READ_USER_DICTIONARIES = no
    AUTOCAD_OD_READ_XREFS = no
    AUTOCAD_OD_RESOLVE_BLOCKS = no
    AUTOCAD_OD_RESOLVE_DIMENSIONS = no
    AUTOCAD_OD_RESOLVE_ENTITY_COLOR = yes
    AUTOCAD_OD_STORE_BULGE_INFO = no
    AUTOCAD_OD_STORE_LAYER_INFO = no
    AUTOCAD_OD_STORE_SPLINE_DEFS = yes
    AUTOCAD_OD_STRUCTURE_EXTENDED_DATA = no
    AUTOCAD_OD_USE_NEW_PAPER_SPACE_PARAMETERS = yes
    AUTOCAD_OD_USE_SEARCH_ENVELOPE = NO
    AUTOCAD_OD_XRECORD_READING = None
    COMBINE_GEOM = Use Result
    DATASET = @Value(path_directory_windows)@Value(path_rootname).@Value(path_extension)
    FORMAT = AUTOCAD_OD
    INTERACT = NONE
    ORDER_RESULTS = No
    OUTPUT_FEATURES_DISPLAY = Data Features
    <OTHER> -> AttributeExposer_3
AttributeExposer_3
    ATTR_LIST = autocad_text_string,autocad_entity_handle,autocad_block_name,autocad_original_entity_type,autocad_attributes_follow
    -> TestFilter_3
TestFilter_3
    DEFAULT_VALUE = <UNFILTERED>
    PASSED_TEST_GROUP_OUTPUT = FIRST
    TEST_LIST:
      "BOOL_OP,AND,COMPOSITE_TEST,""""""1 AND 2"""""",TEST_CLAUSE,TEST autocad_block_name ATTRIBUTE_HAS_A_VALUE ""
      TEST @Value(autocad_attributes_follow) = true",block_name_s_attributy,"BOOL_OP,AND,COMPOSITE_TEST,""""""1"""""",TEST_CLAUSE,TEST autocad_block_name ATTRIBUTE_HAS_A_VALUE """,block_name_bez_attributu,"BOOL_OP,OR,COMPOSITE_TEST,""""""1"""""",TEST_CLAUSE,TEST @Value(autocad_original_entity_type) = autocad_attribute",attribut,"BOOL_OP,OR,COMPOSITE_TEST,""""""1 OR 2 OR 3"""""",TEST_CLAUSE,TEST @Value(autocad_original_entity_type) = autocad_multi_text
      TEST @Value(autocad_original_entity_type) = autocad_text
      TEST @Value(autocad_original_entity_type) = autocad_multi_leader",text,"BOOL_OP,OR,COMPOSITE_TEST,""""""1"""""",TEST_CLAUSE,TEST @Value(autocad_original_entity_type) = autocad_dimension",sdimension
    block_name_s_attributy -> BulkAttributeKeeper_4
Note: MOJE
BulkAttributeKeeper_4
    keepStr = \b[0-9A-Z_]+\b|(autocad_block_name)|(autocad_entity_handle)
    -> AttributeExploder
AttributeExploder
    ATTR_NAME_LABEL = _attr_name
    ATTR_VALUE_LABEL = _attr_value
    EXPLODING_TYPE = List
    KEEP_ATTRIBUTES = Yes
    KEEP_GEOMETRY = No
    LIST_NAME = _attr_list
    -> ListElementFilter
Note: MOJE2
ListElementFilter
    CASE = No
    EXP = fme_|autocad_block_name|autocad_entity_handle
    FILTER_TYPE = REGEX_MATCH
    LIST_ATTR = _attr_list{}._attr_name
    NEGATE = Yes
    Filtered -> ListExploder
ListExploder
    ATTR_ACCUM_MODE = Merge List Attributes
    ATTR_CONFLICT_RES = Use Original Attribute Values
    INDEX_ATTR = _element_index
    LIST_ATTR = _attr_list{}
    ELEMENTS -> AttributeManager
AttributeManager
    ATTR_TABLE:
      RENAME_SET_VALUE _attr_name > Attribute_name (buffer)
      RENAME_SET_VALUE _attr_value > Attribute_value (buffer)
      RENAME_SET_VALUE _element_index > Element_index (uint32)
    USER_EXPOSED_ATTRIBUTES = ID
    -> FeatureWriter_4 [<Rejected>]
FeatureWriter_4
    DATASET = PG_DOKE
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = No
    POSTGRES_NAMED_CONNECTION = PG_DOKE
    POSTGRES_START_TRANSACTION = 0
    POSTGRES_STRICT_TEMPORAL_TYPE_HANDLING = Yes
    POSTGRES_TRANSACTION_INTERVAL = 1000
    TOTAL_FEATURES_WRITTEN_ATTR = _total_features_written

FME custom transformer BulkAttributeKeeper
BulkAttributeKeeper
Keeps all attributes with names that match a given regular expression. This transformer can be used to keep large numbers of attributes that have common naming patterns. By just using a string transform will keep attributes with names that contain the string. 
Negative wrapper for BulkAttributeRemover.

Parameters:
- keepStr =   # Expression to Keep

Input (input)
    -> BulkAttributeRemover
BulkAttributeRemover
    ATTR_EXP = ^(?!.*$(keepStr)).*$
    -> Output (output)
Output (output)

FME custom transformer ListElementFilter
Replaces the specified source list with the same name list containing only elements that match the specified condition. If the source list does not contain matched elements at all, the input feature will be output via the NotFound port without any change.
    This transformer performs filtering with one of these filter types.
    ---------- 
    Has Value
    : Every element in the resulting list stores a value (i.e. non-empty, non-null, non-missing).
    Exact Match
    : Every element in the resulting list stores a value that exact matches the specified string.
    Contains
    : Every element in the resulting list stores a value that contains the specified string.
    Begins With
    : Every element in the resulting list stores a value that begins with the specified string.
    Ends With
    : Every element in the resulting list stores a value that ends with the specified string.
    Regular Expression Match
    : Every element in the resulting list stores a value that matches the specified regular expression.
    Numeric Value
    : Every element in the resulting list stores a numeric value.
    Numeric Range
    : Every element in the resulting list stores a numeric value within the specified range.
    ---------- 
    This transformer treats a null and missing element as an empty string when determining if an element matches the filtering condition
    .
    However, a null or missing element will be propagated to the resulting list as is, if it matches the filtering condition.
    This transformer supports simple lists (e.g. _list{}) and structured lists (e.g. _list{}.foo, _list{}.bar), but doesn't support nested lists (e.g. _list{}.sub{}).
    If a member (component) of a structured list is specified as the source, other members (components) of the same list will also be filtered synchronously with the specified member.
    This transformer differentiates a simple list and structured list having the same base name. For example, when "_base{}" is specified as the source, "_base{}.foo" and "_base{}.bar" won't be processed even though the base name is the same as the source list. Vice versa. 
    If the filtering cannot be performed with an unexpected reason (e.g. malformed regular expression), the input feature will be output via the <Rejected> port, and the rejected features will have an attribute named "_rejected_reason" that stores a string describing the rejected reason.
    Example
    Consider that the input feature has this list - contains 5 elements, index range is 0 to 4.
    _list{}.foo = [1,2,3,4,5]
    _list{}.bar = [a,b,c,d,e]
    If you set the parameters like this:
    - Source List Attribute: 
    _list{}.foo
    - Filter Type: 
    Numeric Range
    - Match Expression: 
    (2,5)
    this expression represents "greater than 2 and less than 5"
    the resulting list will be:
    _list{}.foo = [3,4]
    _list{}.bar = [c,d]
    Here, the number of the resulting elements is 2 and the index range is 0 to 1.
Parameters
    Source List Attribute
    :
    Specify a simple list (e.g. _list{}) or a member of a structured list (e.g. _list{}.foo) that should be filtered.
    Fiter Type
    :
    Select one of these filter types.
---------- 
    Has Value
    : Every element in the resulting list stores a value (i.e. non-empty, non-null, non-missing).
    Exact Match
    : Every element in the resulting list stores a value that exact matches the specified string.
    Contains
    : Every element in the resulting list stores a value that contains the specified string.
    Begins With
    : Every element in the resulting list stores a value that begins with the specified string.
    Ends With
    : Every element in the resulting list stores a value that ends with the specified string.
    Regular Expression Match
    : Every element in the resulting list stores a value that matches the specified regular expression.
    Numeric Value
    : Every element in the resulting list stores a numeric value.
    Numeric Range
    : Every element in the resulting list stores a numeric value within the specified range.
---------- 
    Match Expression
    : 
    In the "Exact Match", "Contains", "Begins With", or "Ends With" type filtering, enter a text string as the filtering condition.
    In the "Regular Expression Match" type filtering, enter a regular expression as the filtering condition.
    In the "Numeric Range" type filtering, specify a numeric range as the filtering condition, with this format.
    ---------- 
    ( or [ 
    lower value
    , 
    upper value
    ) or ]
    - Lower value and upper value should be separated by a comma.
    - Blank for the lower/upper value means unlimited.
    - Round bracket ( ) indicates "excluding the specified value"; square bracket [ ] indicates "including the specified value".
    Examples:
    (0,5) matches any numeric value that is greater than 0 and less than 5. 
    (0,5] matches any numeric value that is greater than 0 and less than or equal to 5.
    [0,5) matches any numeric value that is greater than or equal to 0 and less than 5.
    [0,5] matches any numeric value that is greater than or equal to 0 and less than or equal to 5.
    [0,) matches any numeric value that is greater than or equal to 0.
    (,5) matches any numeric value that is less than 5.
    ----------
    This parameter setting does not affect the result of the "Has Value" and "Numeric Value" type filtering.
    Case Sensitive
    :
    By default, the filtering of "Exact Match" or "Regular Expression Match" type will be performed in case-insensitive. If you set "Yes" to this parameter, the filtering will be performed in case-sensitive.
    This parameter setting does not affect the result of the filtering with other types.
    Negate Filtering Condition
    :
    If you set "Yes" to this parameter, this transformer performs the filtering with the negate condition. For example, if you set "[0,5]" to the "Match Expression" in the "Numeric Range" type filtering and then set "Yes" to this parameter, the resulting list will contain elements that are less than 0 or greater than 5.
    Note: the transformer won't select non-numeric elements in the "Numeric Range" type filtering even if you set "Yes" to the "Negate Filtering Condition" parameter.

Parameters:
- LIST_ATTR =   # " " Source List Attribute
- FILTER_TYPE = HAS_VALUE
- EXP =   # Match Expression
- CASE = No   # Case Sensitive
- NEGATE = No   # Negate Filtering Condition

Input (input)
    -> ParameterFetcher
Note: History of the Tcl Script: / 2016-03-27 Original Implementation / 2016-03-28 Added Filtering Types - "CONTAINS", "BEGINS_WITH", "ENDS_WITH"
ParameterFetcher
    ATTR_LIST = __listelementfilter.list_attr {$(LIST_ATTR)} __listelementfilter.filter_type {$(FILTER_TYPE)} __listelementfilter.case {$(CASE)} __listelementfilter.exp {$(EXP)} __listelementfilter.negate {$(NEGATE)}
    -> TclCaller
TclCaller
    SRC:
      proc filterListElements {} {
          set listAttr [FME_GetAttribute "__listelementfilter.list_attr"]
          if {![regexp {^([^{}]+){}(\.[^{}]+)?$}  $listAttr m base suffix]} {
              return "failed interpreting source list name: $listAttr"
          }

          set maxIndex -1
          set suffixes {}
          if {[string equal $suffix {}]} {
              set listAttrPattern "^$base{(\\d+)}()\$"
          } else {
              set listAttrPattern "^$base{(\\d+)}(\\.\[^{}\]+)\$"
          }
          foreach attr [FME_AttributeNames] {
              if {[regexp $listAttrPattern $attr m i s]} {
                  if {$maxIndex < $i} {
                      set maxIndex $i
                  }
                  if {[lsearch $suffixes $s] < 0} {
                      lappend suffixes $s
                  }
              }
          }

          set isNoCase [string equal [FME_GetAttribute "__listelementfilter.case"] "No"]
          if {$isNoCase} {
              set exp [string tolower [FME_GetAttribute "__listelementfilter.exp"]]
          } else {
              set exp [FME_GetAttribute "__listelementfilter.exp"]
          }
          proc attrValue {attr isNoCase} {
              if {$isNoCase} {
                  return [string tolower [FME_GetAttribute $attr]]
              } else {
                  return [FME_GetAttribute $attr]
              }
          }
          proc matchString {s} {
              return [string map {\\ \\\\ * \\* ? \\? \[ \\\[ \] \\\]} $s]
          }

          set indices {}
          set doMatch 0
          set filterType [FME_GetAttribute "__listelementfilter.filter_type"]
          switch  $filterType {
              "HAS_VALUE" {
                  for {set i 0} {$i <= $maxIndex} {incr i} {
                      if {![string equal [FME_GetAttribute "$base{$i}$suffix"] {}]} {
                          lappend indices $i
                      }
                  }
              }
              "EXACT_MATCH" {
                  for {set i 0} {$i <= $maxIndex} {incr i} {
                      if {[string equal $exp [attrValue "$base{$i}$suffix" $isNoCase]]} {
                          lappend indices $i
                      }
                  }
              }
              "CONTAINS" {set exp "*[matchString $exp]*"; set doMatch 1}
              "BEGINS_WITH" {set exp "[matchString $exp]*"; set doMatch 1}
              "ENDS_WITH" {set exp "*[matchString $exp]"; set doMatch 1}
              "REGEX_MATCH" {
                  for {set i 0} {$i <= $maxIndex} {incr i} {
                      if {[catch {regexp $exp [attrValue "$base{$i}$suffix" $isNoCase]} matched]} {
                          return "failed interpreting regular expression: [FME_GetAttribute __listelementfilter.exp]"
                      } elseif {$matched} {
                          lappend indices $i
                      }
                  }
              }
              "NUMERIC_VALUE" {
                  for {set i 0} {$i <= $maxIndex} {incr i} {
                      if {[string is double -strict [FME_GetAttribute "$base{$i}$suffix"]]} {
                          lappend indices $i
                      }
                  }
              }
              "NUMERIC_RANGE" {
                  set exp [string trim [string map {( < [ <= ) < ] <=} $exp]]
                  if {![regexp {^(<=?)\s*(.*)\s*,\s*(.*)\s*(<=?)$}  $exp m op1 lower upper op2] \
                      || !([string is double $lower] && [string is double $upper])} {
                      return "failed interpreting numeric range expression: [FME_GetAttribute __listelementfilter.exp]"
                  }
                  for {set i 0} {$i <= $maxIndex} {incr i} {
                      set value [FME_GetAttribute "$base{$i}$suffix"]
                      if {[string is double -strict $value] \
                          && ([string equal $lower {}] || [expr $lower $op1 $value]) \
                          && ([string equal $upper {}] || [expr $value $op2 $upper])} {
                          lappend indices $i
                      }
                  }
              }
              default {
                  return "debug - undefined filter type: $filterType"
              }
          }
          if {$doMatch} {
              for {set i 0} {$i <= $maxIndex} {incr i} {
                  if {[string match $exp [attrValue "$base{$i}$suffix" $isNoCase]]} {
                      lappend indices $i
                  }
              }
          }

          if {[string equal [FME_GetAttribute "__listelementfilter.negate"] "Yes"]} {
              set t {}
              set indices [lsort $indices]
              if {[string equal $filterType "NUMERIC_RANGE"]} {
                  for {set i 0} {$i <= $maxIndex} {incr i} {
                      if {[lsearch -sorted $indices $i] < 0 \
                          && [string is double -strict [FME_GetAttribute "$base{$i}$suffix"]]} {
                          lappend t $i
                      }
                  }
              } else {
                  for {set i 0} {$i <= $maxIndex} {incr i} {
                      if {[lsearch -sorted $indices $i] < 0} {
                          lappend t $i
                      }
                  }
              }
              set indices $t
          }

          if {0 < [llength $indices]} {
              set index 0
              foreach oldIndex [lsort -integer $indices] {
                  if {$index != $oldIndex} {
                      foreach s $suffixes {
                          set oldName "$base{$oldIndex}$s"
                          if {[FME_AttributeExists $oldName]} {
                              FME_RenameAttribute "$base{$index}$s" $oldName
                          } else {
                              FME_UnsetAttributes "$base{$index}$s"
                          }
                      }
                  }
                  incr index
              }
              while {$index <= $maxIndex} {
                  foreach s $suffixes {
                      FME_UnsetAttributes "$base{$index}$s"
                  }
                  incr index
              }
              return filtered
          } else {
              return not_found
          }
      }
    TCLPROG = filterListElements
    VAL_ATTR = __listelementfilter.result
    -> TestFilter
TestFilter
    DEFAULT_VALUE = <UNFILTERED>
    TEST_LIST = BOOL_OP,OR,COMPOSITE_TEST,<Unused>,TEST_CLAUSE,"TEST @Value(__listelementfilter.result) = filtered",filtered,BOOL_OP,OR,COMPOSITE_TEST,<Unused>,TEST_CLAUSE,"TEST @Value(__listelementfilter.result) = not_found",not_found
    filtered -> Filtered (output)
    not_found -> NotFound (output)
    <UNFILTERED> -> AttributeRenamer
Filtered (output)
NotFound (output)
AttributeRenamer
    ATTR_LIST = __listelementfilter.result,_rejected_reason,
    -> <Rejected> (output)
<Rejected> (output)
