FME workspace COZ_Projekt_Doplneni_udaju_ku_obec_okres_kraj_stav-urad_na_test.fmw
Title: COZ_Projekt_Doplneni_udaju_ku_obec_okres_kraj_stav-urad
History: 29.3.2023,JH,Verze se seznamem ku, obcí, okresů, krajů, stav. úřadů podle celého polygonu projektu

Creator
    COORDSYS = Czech/JTSK.Krovak
    GEOMTYPE = Geometry Object
    NUM = 1
    CREATED -> FeatureReader_2 [INITIATOR]
    CREATED -> FeatureReader_7 [INITIATOR]
    CREATED -> FeatureReader_8 [INITIATOR]
    CREATED -> FeatureReader_9 [INITIATOR]
    CREATED -> FeatureReader_3 [INITIATOR]
FeatureReader_2
    ATTRIBUTES = GISOZETB.OZ_PROJEKT,"FID,AREA,DATUM_UPRAV,DATUM_VYTVOR,ID_ACCESS,ID_PRIORITA,ID_STAV,ID_TYP,NAZEV,PLOCHA,PORAD_CISLO,POZNAMKA,SPP_PRVEK,USER_UPRAV,USER_VYTVOR,VYKON,OLD_FID,ID_DRUH,FID_BOD_PRIPOJENI,KATUZ_KOD,KATUZ_NAZEV,ZSJ_KOD,ZSJ_NAZEV,OBEC_KOD,OBEC_NAZEV,OKRES_KOD,OKRES_NAZEV,VUSC_KOD,VUSC_NAZEV,STAV_URAD_KOD,STAV_URAD_NAZEV,GEOM_CENTER_POINT_WKT,ID_CLARITY,STAV_CLARITY,FID_OOCOZ,FAZE_CLARITY,ID_BROWNFIELD,DATUM_SCHAV_PROJ,ID_PRIP_OVER,VYKON_INSTALOVANY,ID_DIST_UZEMI,FID_PRIPOJENI,ID_DOT_TITUL,ID_EIA,VYKON_ZTRACENY,DATUM_SITE_VISIT,PLOCHA_CELKEM,SMLOVA_PRIPOJ,DELKA_PRIPOJ,ID_VB,ID_UP,DATUM_ZMENY_UP,DATUM_PODANI_ZMENY_UP,DATUM_PROJED_ZASTUPIT,ID_REZIM,ID_KOMUN_PROJEKT,ID_DRUH_KOMUNIT_PODPORY,VYSE_KOMUNIT_PODPORY,ID_H67,ID_KRAJ_RAZ,FID_PRIPRAVAR_PROJ,FID_PROJEKT_MANAGER,DATUM_PREDANI_KONTROLA,DATUM_PREDANI_ODB_ROZVOJE,DATUM_VYRAZENI,ID_DUVOD_VYRAZENI,ID_SEIA,NUTS_FVE"
    ATTR_ACCUM_MODE = Only Use Result
    COMBINE_GEOM = Use Result
    COORDSYS = Czech/JTSK.Krovak
    DATASET = vyrokt_GISOZETB
    FEATURETYPES = GISOZETB.OZ_PROJEKT
    FORMAT = ORACLE_SPATIAL
    INTERACT = NONE
    ORACLE_SPATIAL_CHUNK_SIZE = 200
    ORACLE_SPATIAL_CREATE_FEATURE_TABLES_FROM_DATA = Yes
    ORACLE_SPATIAL_HANDLE_MULTIPLE_SPATIAL_COLUMNS = NO
    ORACLE_SPATIAL_NAMED_CONNECTION = vyrokp_GISOZETB
    ORACLE_SPATIAL_PARSE_MAPINFO_SYMBOLOGY = NO
    ORACLE_SPATIAL_PERSISTENT_CONNECTION = YES
    ORACLE_SPATIAL_QUERY_FEATURE_TYPES_FOR_MERGE_FILTERS = Yes
    ORACLE_SPATIAL_READ_3D_POLYGON_AS_FACE = NO
    ORACLE_SPATIAL_REMOVE_SCHEMA_QUALIFIER = NO
    ORACLE_SPATIAL_SERVER_TYPE = ORACLE8i
    ORACLE_SPATIAL_SHOW_SYSTEM_TABLES = NO
    ORACLE_SPATIAL_USE_SEARCH_ENVELOPE = NO
    ORACLE_SPATIAL_USE_UNIFIED_DATE_ATTRS = YES
    OUTPUT_FEATURES_DISPLAY = Data Features
    WHERE = ID_DRUH = 1
    GISOZETB.OZ_PROJEKT -> GeometryFilter
    GISOZETB.OZ_PROJEKT -> SQLExecutor [INITIATOR]
GeometryFilter
    FILTER_MODE = SIMPLE
    FILTER_MULTI = FILTER_TYPES]Area]FME_CONTROLLER_QUERY_FILE]]FME_CONTROLLER_CHOICE]Simple
    Area -> ChangeDetector [ORIGINAL]
    <UNFILTERED> -> ChangeDetector [ORIGINAL]
Note: Načtení parcel k projektům
SQLExecutor
    COMBINE_ATTRS = Result Attributes Only
    COMBINE_GEOM = Result Geometry Only
    COORDSYS = Czech/JTSK.Krovak
    DATASET = vyrokt_GISOZETB
    EXPOSED_ATTRIBUTE_LIST = FID,AREA,CIS_SML,DRUH_CISLOVANI_KOD,DRUH_POZEMKU_KOD,DUVOD,ID,ID_KLASIFIKACE,ID_STAV,KATUZ_KOD,KMENOVE_CISLO,NESPRAVNY,PLATI_OD,PODDELENI_CISLA,POZNAMKA,PUVOD,RIZENI_ID,VYMERA_PARCELY,ZPUSOB_VYU_POZ_KOD,ID_TRANS_RUIAN,FID_SMLOUVA,FID_PROJEKT
    FORMAT = ORACLE_SPATIAL
    ORACLE_SPATIAL_CREATE_FEATURE_TABLES_FROM_DATA = Yes
    ORACLE_SPATIAL_NAMED_CONNECTION = vyrokp_GISOZETB
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = NO
    ORACLE_SPATIAL_USE_UNIFIED_DATE_ATTRS = YES
    OUTPUT_FEATURES_DISPLAY = Schema and Data Features
    SQL_STATEMENT = select a.*,b.FID_PROJEKT from OZ_MN_PROJEKT b left join OZ_PARC a on b.FID_PARC = a.FID where b.FID_PROJEKT = @Value(FID)
    RESULT -> AttributeKeeper
    RESULT -> AttributeManager_2
    INITIATOR -> AttributeFilter
FeatureJoiner
    ATTR_CONFLICT_RES = Prefer Left
    GEOMETRY_HANDLING = Prefer Left
    JOIN_KEYS = FID FID AUTO
    JOIN_MODE = Inner
    JOINED -> FeatureJoiner_6 [LEFT]
GeometryRemover_2
    REMOVE_COORDSYS = No
    -> DuplicateFilter
DuplicateFilter
    INPUT_ORDERED_CHOICE = No
    KEYATTR = FID
    UNIQUE -> FeatureJoiner_4 [LEFT]
    UNIQUE -> FeatureJoiner_5 [LEFT]
FeatureJoiner_6
    ATTR_CONFLICT_RES = Prefer Left
    GEOMETRY_HANDLING = Prefer Left
    JOIN_KEYS = FID FID AUTO
    JOIN_MODE = Inner
    JOINED -> AttributeManager_7
AttributeManager_7
    ATTR_TABLE:
      REMOVE _timestamp
      REMOVE _x
      REMOVE _y
    -> ChangeDetector [REVISED]
ChangeDetector
    BLANK_AND_MISSING_DIFFER = No
    CHECK_COORDINATE_SYSTEMS = No
    CHECK_TYPES_AND_ENCODINGS = No
    LENIENT_MATCH = No
    MATCH = 2D
    MATCHATTRS = GEOM_CENTER_POINT_WKT KATUZ_KOD KATUZ_NAZEV OBEC_KOD OBEC_NAZEV OKRES_KOD OKRES_NAZEV STAV_URAD_KOD STAV_URAD_NAZEV VUSC_KOD VUSC_NAZEV ZSJ_KOD ZSJ_NAZEV NUTS_FVE
    MATCH_STRATEGY = Match Selected Attributes
    PREEMPTIVE_ATTRS = FID
    UNCHANGED_OUTPUT = Output Original
    UPSERT_MODE = No
    UPDATED -> FeatureWriter [GISOZE.PROJEKT]
    INSERTED -> FeatureWriter [GISOZE.PROJEKT]
FeatureWriter
    DATASET = vyrokt_GISOZETB
    DATASET_ATTR = _dataset
    FEATURE_TYPE_LIST_ATTR = _feature_types
    FORMAT = ORACLE_SPATIAL
    ORACLE_SPATIAL_CHUNK_SIZE = 200
    ORACLE_SPATIAL_CONTAINS_MEASURES = NO
    ORACLE_SPATIAL_CREATE_SPATIAL_INDEX = no
    ORACLE_SPATIAL_DIMENSION = 2
    ORACLE_SPATIAL_GEOMETRY_COLUMN = GEOM
    ORACLE_SPATIAL_HANDLE_MULTIPLE_SPATIAL_COLUMNS = NO
    ORACLE_SPATIAL_INDEX_LEVELS = 0
    ORACLE_SPATIAL_NAMED_CONNECTION = vyrokp_GISOZETB
    ORACLE_SPATIAL_NONQUOTED_OBJECT_NAMES = Yes
    ORACLE_SPATIAL_NUMBER_OF_TILES = 8
    ORACLE_SPATIAL_PERSISTENT_CONNECTION = YES
    ORACLE_SPATIAL_SERVER_TYPE = ORACLE8i
    ORACLE_SPATIAL_SPATIAL_INDEX_MAXX = 180
    ORACLE_SPATIAL_SPATIAL_INDEX_MAXY = 90
    ORACLE_SPATIAL_SPATIAL_INDEX_MINX = -180
    ORACLE_SPATIAL_SPATIAL_INDEX_MINY = -90
    ORACLE_SPATIAL_START_TRANSACTION = 0
    ORACLE_SPATIAL_STRICT_ATTR_CONVERSION = No
    ORACLE_SPATIAL_TRANSACTION_INTERVAL = 1000
    TOTAL_FEATURES_WRITTEN_ATTR = _total_features_written

Bookmark: Vytvoření obvodu projektu
AttributeKeeper
    CREATE_BULK_MODE_FEATURES = NO
    KEEP_ATTRS = FID_PROJEKT,ID
    -> AttributeRenamer
AttributeRenamer
    ATTR_TABLE = RENAME_SET_DEFAULT FID_PROJEKT > FID
    MISSING_INPUT_ATTRS = REMOVE
    -> CoordinateSystemSetter
CoordinateSystemSetter
    COORDSYS = Czech/JTSK.Krovak
    -> HullAccumulator
HullAccumulator
    3DMODE_PARAM = 2D
    ACCUM_INPUT_ATTRS = Use Attributes From One Feature
    GROUP_BY = FID
    HULLTYPE_PARAM = Convex ()
    HULL -> AttributeKeeper_2
    HULL -> GeometryRemover_2
AttributeKeeper_2
    CREATE_BULK_MODE_FEATURES = NO
    KEEP_ATTRS = FID
    -> Bufferer_2
Bufferer_2
    ANGLE = 22.5
    CAP_STYLE = Round
    CORNER_STYLE = Round
    MODE = AREA
    OFFSET = 5
    OFFSET_UNITS = METERS
    PRECISION = APPROX
    BUFFERED -> DateTimeStamper_2
DateTimeStamper_2
    DATETIME_ATTR = _timestamp
    INCLUDE_FRAC_SECONDS = YES
    STAMP_TYPE = date
    TIMEZONE = utc
    -> AttributeManager_3
    -> SpatialRelator [Requestor]
AttributeManager_3
    ATTR_TABLE:
      REMOVE fme_feature_type
      REMOVE autocad_block_name
      REMOVE autocad_color
      REMOVE autocad_entity
      REMOVE autocad_layer
      REMOVE autocad_linetype
      REMOVE autocad_linetype_scale
      REMOVE autocad_lineweight
      REMOVE autocad_original_entity_type
      REMOVE autocad_original_rotation
      REMOVE autocad_rotation
      REMOVE autocad_source_filename
      REMOVE autocad_text_rotation
      REMOVE autocad_text_size
      REMOVE autocad_text_string
      REMOVE fme_basename
      REMOVE fme_dataset
      REMOVE fme_type
      REMOVE _substring
    -> CoordinateRounder
CoordinateRounder
    XPREC = 3
    YPREC = 3
    ZPREC = 3
    ROUNDED -> GeometryCoercer_3
GeometryCoercer_3
    GQUERY:
      for $geom in //geometry
      where $geom/count(parent::geometry) = 0
      return number($geom/@fme_id)
    KIND = fme_polygon
    COERCED -> CenterPointReplacer
    COERCED -> FeatureJoiner [LEFT]

Bookmark: Vytvoření CENTROIDu polygonu WKT
CenterPointReplacer
    POINTTYPE = CENTEROFGRAV
    POINT -> Reprojector
    POINT -> SpatialRelator_2 [Requestor]
Reprojector
    DEST = EPSG:4326
    INTERPOLATION_TYPE_NAME = Nearest Neighbor
    RASTER_CELL_SIZE = Preserve Cells
    RASTER_TOLERANCE = 0.0
    REPROJECTED -> CoordinateExtractor
CoordinateExtractor
    IND = 0
    MODE = Specify Coordinate
    X_ATTR = _x
    Y_ATTR = _y
    Z_ATTR = _z
    -> AttributeManager
AttributeManager
    ATTR_TABLE:
      SET_TO _x = @Evaluate(@real32(@XValue()))
      SET_TO _y = @Evaluate(@real32(@YValue()))
      REMOVE _z
      SET_TO GEOM_CENTER_POINT_WKT = @Value(_y), @Value(_x)
    -> GeometryRemover
GeometryRemover
    REMOVE_COORDSYS = No
    -> StringReplacer
StringReplacer
    CASE = NO
    FIND_TEXT = POINT [(]|[)]
    NO_MATCH = _FME_NO_OP_
    REGEXP = YES
    SRC_ATTRS = GEOM_CENTER_POINT_WKT
    -> FeatureJoiner [RIGHT]

Bookmark: Odebrání geometrie
AttributeFilter
    ATTR_NAME = _matched_records
    ATTR_VALUES = <Empty>,<Missing>,<Null>,<Unfiltered>,0
    0 -> GeometryRemover_3
GeometryRemover_3
    REMOVE_COORDSYS = No
    -> ChangeDetector [REVISED]

Bookmark: Vytvoření seznamu parcel k projektu
AttributeManager_2 [off]
    ATTR_TABLE = SET_TO PAR_CIS = FME_CONDITIONAL:DEFAULT_VALUE'@Value(KMENOVE_CISLO) (@Value(KATUZ_KOD))'BOOL_OP;OR;COMPOSITE_TEST;1;TEST PODDELENI_CISLA ATTRIBUTE_HAS_A_VALUE _FME_BLANK_STRING_'@Value(KMENOVE_CISLO)/@Value(PODDELENI_CISLA) (@Value(KATUZ_KOD))'FME_NUM_CONDITIONS2___
    -> ListBuilder [off]
ListBuilder [off]
    GROUP_BY = FID_PROJEKT
    LIST_ATTRS_TO_INCLUDE = PAR_CIS
    LIST_NAME = LIST_PARC
    -> ListConcatenator [off]
ListConcatenator [off]
    DROP_EMPTY_PARTS = No
    LIST_ATTR = LIST_PARC{}.PAR_CIS
    SEP = "; "
    VAL_ATTR = SEZNAM_PARCEL
    -> FeatureJoiner_4 [RIGHT] [off]
FeatureJoiner_4 [off]
    ATTR_CONFLICT_RES = Prefer Left
    GEOMETRY_HANDLING = Prefer Left
    JOIN_KEYS = FID_PROJEKT FID_PROJEKT AUTO
    JOIN_MODE = Inner

Bookmark: Stavební úřady
Note: Postgis
FeatureReader_7
    ATTRIBUTES = ruian.rn_zsj_p,"fid,area,charakter_zsj_kod,id_trans_ruian,katuz_kod,kod,mluv_char_pad_2,mluv_char_pad_3,mluv_char_pad_4,mluv_char_pad_5,mluv_char_pad_6,mluv_char_pad_7,nazev,nespravny,nz_id_globalni,plati_od,vymera,zmena_grafiky,puvod"
    ATTR_ACCUM_MODE = Only Use Result
    COMBINE_GEOM = Use Result
    COORDSYS = EPSG:5514
    DATASET = cw00605pfmedb_FME_RUIAN
    FEATURETYPES = ruian.rn_zsj_p
    FORMAT = POSTGIS
    INTERACT = NONE
    OUTPUT_FEATURES_DISPLAY = Data Features
    POSTGIS_CREATE_FEATURE_TABLES_FROM_DATA = Yes
    POSTGIS_DISABLE_COLLECTION_SPLITTING = yes
    POSTGIS_FEATURES_PER_FETCH = 10000
    POSTGIS_NAMED_CONNECTION = cw00605pfmedb_ruian_all
    POSTGIS_QUERY_FEATURE_TYPES_FOR_MERGE_FILTERS = Yes
    POSTGIS_READ_TIME_WITH_TIMEZONE = Yes
    POSTGIS_SCHEMAS_FOR_TABLE_LISTING = ruian public
    POSTGIS_USE_SEARCH_ENVELOPE = NO
    POSTGIS_USE_TRUE_POSTGIS_TYPES = yes
    ruian.rn_zsj_p -> DuplicateFilter_2
DuplicateFilter_2
    INPUT_ORDERED_CHOICE = No
    KEYATTR = area fid charakter_zsj_kod id_trans_ruian katuz_kod kod mluv_char_pad_2 mluv_char_pad_3 mluv_char_pad_4 mluv_char_pad_5 mluv_char_pad_6 mluv_char_pad_7 nazev nespravny nz_id_globalni plati_od puvod vymera zmena_grafiky
    UNIQUE -> AttributeManager_4
AttributeManager_4
    ATTR_TABLE:
      REMOVE fid
      REMOVE area
      REMOVE charakter_zsj_kod
      REMOVE id_trans_ruian
      RENAME_SET_VALUE katuz_kod > KATUZ_KOD
      RENAME_SET_VALUE kod > ZSJ_KOD
      REMOVE mluv_char_pad_2
      REMOVE mluv_char_pad_3
      REMOVE mluv_char_pad_4
      REMOVE mluv_char_pad_5
      REMOVE mluv_char_pad_6
      REMOVE mluv_char_pad_7
      RENAME_SET_VALUE nazev > ZSJ_NAZEV
      REMOVE nespravny
      REMOVE nz_id_globalni
      REMOVE plati_od
      REMOVE vymera
      REMOVE zmena_grafiky
      REMOVE puvod
    -> FeatureJoiner_2 [LEFT]
Note: PostgreSQL
FeatureReader_8
    ATTRIBUTES = vazby.csu_vazba,"kodjaz,typvaz,akrcis1,kodcis1,chodnota1,text1,akrcis2,kodcis2,chodnota2,text2"
    ATTR_ACCUM_MODE = Only Use Result
    COMBINE_GEOM = Use Result
    DATASET = cw00605pfmedb_CSU
    FEATURETYPES = vazby.csu_vazba
    FORMAT = POSTGRES
    OUTPUT_FEATURES_DISPLAY = Data Features
    POSTGRES_CREATE_FEATURE_TABLES_FROM_DATA = Yes
    POSTGRES_FEATURES_PER_FETCH = 10000
    POSTGRES_NAMED_CONNECTION = cw00605pfmedb_CSU
    POSTGRES_QUERY_FEATURE_TYPES_FOR_MERGE_FILTERS = Yes
    POSTGRES_READ_TIME_WITH_TIMEZONE = Yes
    POSTGRES_SCHEMAS_FOR_TABLE_LISTING = vazby
    vazby.csu_vazba -> AttributeManager_5
AttributeManager_5
    ATTR_TABLE:
      REMOVE kodjaz
      REMOVE typvaz
      REMOVE akrcis1
      REMOVE kodcis1
      RENAME_SET_VALUE chodnota1 > STAV_URAD_KOD
      RENAME_SET_VALUE text1 > STAV_URAD_NAZEV
      REMOVE akrcis2
      REMOVE kodcis2
      RENAME_SET_VALUE chodnota2 > ZSJ_KOD
      REMOVE text2
    -> FeatureJoiner_2 [RIGHT]
FeatureJoiner_2
    ATTR_CONFLICT_RES = Prefer Left
    GEOMETRY_HANDLING = Prefer Left
    JOIN_KEYS = ZSJ_KOD ZSJ_KOD AUTO
    JOIN_MODE = Inner
    JOINED -> Junction
    UNJOINED_LEFT -> Junction
Junction
    -> FeatureJoiner_3 [LEFT]

Bookmark: Doplnění Název KÚ až Kraj
Note: PostgreSQL
FeatureReader_9
    ATTRIBUTES = ruian.v_vazba_ku_az_kraj,"kod_katuz,nazev_katuz,kod_obec,nazev_obec,kod_okres,nazev_okres,kod_kraj,nazev_kraj"
    ATTR_ACCUM_MODE = Only Use Result
    COMBINE_GEOM = Use Result
    DATASET = cw00605pfmedb_FME_RUIAN
    FEATURETYPES = ruian.v_vazba_ku_az_kraj
    FORMAT = POSTGRES
    OUTPUT_FEATURES_DISPLAY = Data Features
    POSTGRES_CREATE_FEATURE_TABLES_FROM_DATA = Yes
    POSTGRES_FEATURES_PER_FETCH = 10000
    POSTGRES_NAMED_CONNECTION = cw00605pfmedb_ruian_all
    POSTGRES_QUERY_FEATURE_TYPES_FOR_MERGE_FILTERS = Yes
    POSTGRES_READ_TIME_WITH_TIMEZONE = Yes
    POSTGRES_SCHEMAS_FOR_TABLE_LISTING = ruian
    ruian.v_vazba_ku_az_kraj -> AttributeManager_6
AttributeManager_6
    ATTR_TABLE:
      RENAME_SET_VALUE kod_katuz > KATUZ_KOD
      RENAME_SET_VALUE nazev_katuz > KATUZ_NAZEV
      RENAME_SET_VALUE kod_obec > OBEC_KOD
      RENAME_SET_VALUE nazev_obec > OBEC_NAZEV
      RENAME_SET_VALUE kod_okres > OKRES_KOD
      RENAME_SET_VALUE nazev_okres > OKRES_NAZEV
      RENAME_SET_VALUE kod_kraj > VUSC_KOD
      RENAME_SET_VALUE nazev_kraj > VUSC_NAZEV
    -> FeatureJoiner_7 [LEFT]
FeatureJoiner_3
    ATTR_CONFLICT_RES = Prefer Left
    GEOMETRY_HANDLING = Prefer Left
    JOIN_KEYS = KATUZ_KOD KATUZ_KOD AUTO
    JOIN_MODE = Inner
    JOINED -> SpatialRelator_2 [Supplier]
    JOINED -> SpatialRelator [Supplier]

Bookmark: Tvorba NUTS pro FVE
Note: PostgreSQL
FeatureReader_3
    ATTRIBUTES = ruian.rn_okres_p,"fid,area,id_trans_ruian,kod,kraj_1960_kod,nazev,nespravny,nuts_lau,nz_id_globalni,plati_od,vusc_kod,zmena_grafiky,puvod"
    ATTR_ACCUM_MODE = Only Use Result
    COMBINE_GEOM = Use Result
    DATASET = cw00605pfmedb_FME_RUIAN
    FEATURETYPES = ruian.rn_okres_p
    FORMAT = POSTGRES
    OUTPUT_FEATURES_DISPLAY = Data Features
    POSTGRES_CREATE_FEATURE_TABLES_FROM_DATA = Yes
    POSTGRES_FEATURES_PER_FETCH = 10000
    POSTGRES_NAMED_CONNECTION = cw00605pfmedb_ruain_all
    POSTGRES_QUERY_FEATURE_TYPES_FOR_MERGE_FILTERS = Yes
    POSTGRES_READ_TIME_WITH_TIMEZONE = Yes
    POSTGRES_SCHEMAS_FOR_TABLE_LISTING = ruian
    ruian.rn_okres_p -> AttributeManager_8
AttributeManager_8
    ATTR_TABLE:
      REMOVE fid
      REMOVE area
      REMOVE id_trans_ruian
      SET_TO NUTS_FVE = FV@Substring(@Value(nuts_lau),3)_
      REMOVE kraj_1960_kod
      REMOVE nazev
      REMOVE nespravny
      REMOVE nz_id_globalni
      REMOVE plati_od
      REMOVE vusc_kod
      REMOVE zmena_grafiky
      REMOVE puvod
    -> FeatureJoiner_7 [RIGHT]
FeatureJoiner_7
    ATTR_CONFLICT_RES = Prefer Left
    GEOMETRY_HANDLING = Prefer Left
    JOIN_KEYS = OKRES_KOD kod AUTO
    JOIN_MODE = Inner
    JOINED -> AttributeRemover
    <REJECTED> -> AttributeRemover
AttributeRemover
    REMOVE_ATTRS = kod,nuts_lau
    -> FeatureJoiner_3 [RIGHT]

Bookmark: VAR1 - Přiřazení KÚ až STAV_URAD
SpatialRelator_2
    AGGREGATE_HANDLING = Yes
    ATTR_ACCUM_MODE = Merge Supplier
    ATTR_CONFLICT_RES = Use Requestor
    CALC_CARD = No
    CURVE_BOUNDARY_RULE_PARAM = Default Rule
    IGNORE_NULLS = Yes
    PREDICATES = INTERSECTS
    SUCCESS_ATTR = _related_suppliers
    -> FeatureJoiner_5 [RIGHT]
FeatureJoiner_5
    ATTR_CONFLICT_RES = Prefer Left
    GEOMETRY_HANDLING = Prefer Left
    JOIN_KEYS = FID FID AUTO
    JOIN_MODE = Inner
    JOINED -> AttributeRemover_4
    UNJOINED_LEFT -> AttributeRemover_4
Note: Odstranění nadbytečných attr (FID) a všech listů
AttributeRemover_4
    REMOVE_ATTRS = _related_suppliers
    -> FeatureJoiner_6 [RIGHT]

Bookmark: Vytvoření seznamů KÚ až STAV_URAD
SpatialRelator [off]
    AGGREGATE_HANDLING = Yes
    CALC_CARD = No
    CURVE_BOUNDARY_RULE_PARAM = Default Rule
    LIST_ATTRS_TO_INCLUDE = chodnota1 text1 kod_katuz kod_kraj kod_obec kod_okres nazev_katuz nazev_kraj nazev_obec nazev_okres
    LIST_NAME = _relationships
    PREDICATES = INTERSECTS
    SUCCESS_ATTR = _related_suppliers
    -> ListDuplicateRemover_2 [off]
ListDuplicateRemover_2 [off]
    SRC_LIST = _relationships{}.nazev_katuz
    -> NAZEV_KATUZ [off]
NAZEV_KATUZ: ListConcatenator [off]
    DROP_EMPTY_PARTS = No
    LIST_ATTR = _relationships{}.nazev_katuz
    SEP = "; "
    VAL_ATTR = SEZNAM_NAZEV_KATUZ
    -> ListDuplicateRemover_3 [off]
ListDuplicateRemover_3 [off]
    SRC_LIST = _relationships{}.nazev_obec
    -> NAZEV_OBEC [off]
NAZEV_OBEC: ListConcatenator [off]
    DROP_EMPTY_PARTS = No
    LIST_ATTR = _relationships{}.nazev_obec
    SEP = "; "
    VAL_ATTR = SEZNAM_NAZEV_OBEC
    -> ListDuplicateRemover_4 [off]
ListDuplicateRemover_4 [off]
    SRC_LIST = _relationships{}.nazev_okres
    -> NAZEV_OKRES [off]
NAZEV_OKRES: ListConcatenator [off]
    DROP_EMPTY_PARTS = No
    LIST_ATTR = _relationships{}.nazev_okres
    SEP = "; "
    VAL_ATTR = SEZNAM_NAZEV_OKRES
    -> ListDuplicateRemover_5 [off]
ListDuplicateRemover_5 [off]
    SRC_LIST = _relationships{}.nazev_kraj
    -> NAZEV_KRAJ [off]
NAZEV_KRAJ: ListConcatenator [off]
    DROP_EMPTY_PARTS = No
    LIST_ATTR = _relationships{}.nazev_kraj
    SEP = "; "
    VAL_ATTR = SEZNAM_NAZEV_KRAJ
    -> ListDuplicateRemover_6 [off]
ListDuplicateRemover_6 [off]
    SRC_LIST = _relationships{}.text1
    -> NAZEV_STAV_URAD [off]
NAZEV_STAV_URAD: ListConcatenator [off]
    DROP_EMPTY_PARTS = No
    LIST_ATTR = _relationships{}.text1
    SEP = "; "
    VAL_ATTR = SEZNAM_NAZEV_STAV_URAD
