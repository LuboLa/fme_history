FME workspace COZ_Access_update_OZ_PROJEKT_OZ_PARC_do_testu.fmw

Parameters:
- SourceDataset_MDB_ADO = D:\OZE\Access\Copy\ProjektyOZE_DB1_be.accdb   # Database Path
- SourceDataset_ORACLE_NONSPATIAL = vyrokp_GISDVTBNAV   # Connection
- SourceDataset_ORACLE_SPATIAL_2 = vyrokt_GISOZETB   # Connection
- DestDataset_XLSXW_3 = D:\DATA\COZ\Access_kontrola   # Destination Microsoft Excel File
- DestDataset_ORACLE_NONSPATIAL = vyrokt_GISOZETB   # Connection
- SourceDataset_ORACLE_NONSPATIAL_2 = vyrokt_GISOZETB   # Connection

Readers:
- MDB_ADO_1: MDB_ADO from $(SourceDataset_MDB_ADO)
- ORACLE_NONSPATIAL_1: ORACLE_NONSPATIAL from $(SourceDataset_ORACLE_NONSPATIAL)
- ORACLE_SPATIAL_3: ORACLE_SPATIAL from $(SourceDataset_ORACLE_SPATIAL_2)
- ORACLE_NONSPATIAL_3: ORACLE_NONSPATIAL from $(SourceDataset_ORACLE_NONSPATIAL_2)

Writers:
- XLSXW_2: XLSXW to $(DestDataset_XLSXW_3)
- ORACLE_NONSPATIAL_2: ORACLE_NONSPATIAL to $(DestDataset_ORACLE_NONSPATIAL)

OZ_PROJEKT (reader ORACLE_SPATIAL_3)
    attributes: FID number(10,0), AREA number(20,8), DATUM_UPRAV date, DATUM_VYTVOR date, ID_ACCESS number(10,0), ID_PRIORITA number(10,0), ID_STAV number(10,0), ID_TYP number(10,0), NAZEV varchar2(1020), PLOCHA number(10,3), PORAD_CISLO number(10,0), POZNAMKA varchar2(1020), SPP_PRVEK varchar2(1020), USER_UPRAV varchar2(1020), USER_VYTVOR varchar2(1020), VYKON number(10,3), OLD_FID number(10,0)
    -> FeatureJoiner [RIGHT]
Projekt (reader MDB_ADO_1)
    attributes: ID autonumber, NazevProj text(255), GPS text(255), StavProjektu text(255), SPPCOZ text(255), Vykon decimal(18,2), PlochaProj long, TypProj text(255), Brownfield yesno, PassportKontrola datetime, PassportFinal datetime, Datum provedení site visit datetime, DatumSchvaleniProjektu datetime, PripOver text(255), SmlouvaPripoj text(255), InstalovanyVykon decimal(18,2), DistribUzemi text(255), Délka přípojky (m) long, VBzajistena yesno, KomProj yesno, DruhKomPodp text(255), VyseKomPodp currency, PopisKomPodp text(255), PopisProj memo, PripravarProjektu long, ManagerProjektu long, Priorita long, DuvodVyrProj text(255), KomentVyrProj memo, DatumUP datetime,
      DatumPripoj datetime, DatumZalozeniProj datetime, DatumVyrazeniProj datetime, DatumPasProj datetime, DatumZmenaUP datetime, DatumSouhlasZastUP datetime, SchvalenaZmenaUPzast yesno, UP yesno, ZkracenyRezim yesno, Ztracený výkon DS long, DotacniTitul text(255), EIA text(255), SEIA text(255), H67 text(255), HodnoceníKrajRaz text(255)
    -> FeatureJoiner [LEFT]
FeatureJoiner
    ATTR_CONFLICT_RES = Prefer Left
    GEOMETRY_HANDLING = Prefer Left
    JOIN_KEYS = ID ID_ACCESS AUTO
    JOIN_MODE = Inner
    UNJOINED_LEFT -> NoFeaturesTester
NoFeaturesTester
    NOINPUT -> FeatureHolder
    -> FeatureWriter [GISOZETB.OZ_PROJEKT]
FeatureWriter
    DATASET = vyrokt_GISOZETB
    DATASET_ATTR = _dataset
    FEATURE_TYPE_LIST_ATTR = _feature_types
    FORMAT = ORACLE_SPATIAL
    ORACLE_SPATIAL_CHUNK_SIZE = 200
    ORACLE_SPATIAL_CONTAINS_MEASURES = NO
    ORACLE_SPATIAL_CREATE_SPATIAL_INDEX = no
    ORACLE_SPATIAL_DIMENSION = 2
    ORACLE_SPATIAL_GEOMETRY_COLUMN = GEOM
    ORACLE_SPATIAL_HANDLE_MULTIPLE_SPATIAL_COLUMNS = NO
    ORACLE_SPATIAL_INDEX_LEVELS = 0
    ORACLE_SPATIAL_NAMED_CONNECTION = vyrokp_GISOZETB
    ORACLE_SPATIAL_NONQUOTED_OBJECT_NAMES = Yes
    ORACLE_SPATIAL_NUMBER_OF_TILES = 8
    ORACLE_SPATIAL_PERSISTENT_CONNECTION = YES
    ORACLE_SPATIAL_SERVER_TYPE = ORACLE8i
    ORACLE_SPATIAL_SPATIAL_INDEX_MAXX = 180
    ORACLE_SPATIAL_SPATIAL_INDEX_MAXY = 90
    ORACLE_SPATIAL_SPATIAL_INDEX_MINX = -180
    ORACLE_SPATIAL_SPATIAL_INDEX_MINY = -90
    ORACLE_SPATIAL_START_TRANSACTION = 0
    ORACLE_SPATIAL_STRICT_ATTR_CONVERSION = No
    ORACLE_SPATIAL_TRANSACTION_INTERVAL = 1000
    TOTAL_FEATURES_WRITTEN_ATTR = _total_features_written
    SUMMARY -> FeatureHolder
FeatureHolder
    -> FeatureReader_2 [INITIATOR]
Note: Projekty z vazební tabulky
FeatureReader_2
    ATTRIBUTES = GISOZETB.OZ_PROJEKT,"FID,AREA,DATUM_UPRAV,DATUM_VYTVOR,ID_ACCESS,ID_PRIORITA,ID_STAV,ID_TYP,NAZEV,PLOCHA,PORAD_CISLO,POZNAMKA,SPP_PRVEK,USER_UPRAV,USER_VYTVOR,VYKON,OLD_FID"
    ATTR_ACCUM_MODE = Only Use Result
    COMBINE_GEOM = Use Result
    DATASET = vyrokt_GISOZETB
    FEATURETYPES = GISOZETB.OZ_PROJEKT
    FORMAT = ORACLE_SPATIAL
    INTERACT = NONE
    ORACLE_SPATIAL_CHUNK_SIZE = 200
    ORACLE_SPATIAL_CREATE_FEATURE_TABLES_FROM_DATA = Yes
    ORACLE_SPATIAL_HANDLE_MULTIPLE_SPATIAL_COLUMNS = NO
    ORACLE_SPATIAL_NAMED_CONNECTION = vyrokp_GISOZETB
    ORACLE_SPATIAL_PARSE_MAPINFO_SYMBOLOGY = NO
    ORACLE_SPATIAL_PERSISTENT_CONNECTION = YES
    ORACLE_SPATIAL_QUERY_FEATURE_TYPES_FOR_MERGE_FILTERS = Yes
    ORACLE_SPATIAL_READ_3D_POLYGON_AS_FACE = NO
    ORACLE_SPATIAL_REMOVE_SCHEMA_QUALIFIER = NO
    ORACLE_SPATIAL_SERVER_TYPE = ORACLE8i
    ORACLE_SPATIAL_SHOW_SYSTEM_TABLES = NO
    ORACLE_SPATIAL_USE_SEARCH_ENVELOPE = NO
    ORACLE_SPATIAL_USE_UNIFIED_DATE_ATTRS = YES
    OUTPUT_FEATURES_DISPLAY = Schema and Data Features
    GISOZETB.OZ_PROJEKT -> FeatureMerger_5 [SUPPLIER]
    GISOZETB.OZ_PROJEKT -> FeatureJoiner_2 [RIGHT]
Pozemek (reader MDB_ADO_1)
    attributes: ID autonumber, ParcCislo text(20), DruhPoz text(255), CisloLV long, KatastrUzemi long, VymPoz long, VyuzVymera long, Vyneti yesno, CenaVyneti currency, InfoVyneti text(50), PopisUP text(255), SouladUP yesno, Transakce text(40), PopisPoz memo, AktVyuz text(255), VB_cizi text(255), NameProjekt long, OOCOZ long, DateEvid datetime, OwnerPoz memo, Smlouva long, NOGODuvodSez long, NOGODuvodText memo, PlochaBPEJ1 long, PlochaBPEJ2 long, PlochaBPEJ3 long, PlochaBPEJ4 long, PlochaBPEJ5 long, VymSluz long, DelkaSluz long,
      PopisSluz text(255)
    -> AttributeCreator
AttributeCreator
    ATTR_TABLE:
      SET_TO datumdenminus = @DateTimeAdd(@DateTimeFormat(@DateTimeNow(),%Y%m%d%H%M%S),-P1D)
      SET_TO datummesicminus = @DateTimeAdd(@DateTimeFormat(@DateTimeNow(),%Y%m%d%H%M%S),-P1M)
    -> TestFilter
TestFilter
    DEFAULT_VALUE = <UNFILTERED>
    PASSED_TEST_GROUP_OUTPUT = FIRST
    TEST_LIST = "BOOL_OP,OR,COMPOSITE_TEST,""""""1"""""",TEST_CLAUSE,TEST @Value(DateEvid) > @Value(datumdenminus)",@Value(DateEvid) > @Value(datumdenminus),"BOOL_OP,OR,COMPOSITE_TEST,""""""1"""""",TEST_CLAUSE,TEST @Value(DateEvid) > @Value(datummesicminus)",@Value(DateEvid) > @Value(datummesiccminus)
    @Value(DateEvid) > @Value(datummesiccminus) -> FeatureMerger_5 [REQUESTOR]
    <UNFILTERED> -> FeatureMerger_4 [REQUESTOR]
FeatureMerger_5
    ATTR_ACCUM_MODE = Merge Supplier
    ATTR_CONFLICT_RES = Use Requestor
    IGNORE_NULLS = No
    JOIN_KEYS = @Value(NameProjekt) @Value(ID_ACCESS) AUTO
    MERGE_TYPE = Attributes Only
    PROCESS_DUPS = NO
    REJECT_NULL_MISSING_KEYS = No
    SUPPLIERS_FIRST = No
    MERGED -> FeatureMerger [REQUESTOR]
tab_KU (reader MDB_ADO_1)
    attributes: ID autonumber, KRAJ_KOD long, OKRES_NAZEV text(255), OBEC_NAZEV text(255), KU_KOD double, KU_NAZEV text(255), PRARES_NAZEV text(255)
    -> FeatureMerger [SUPPLIER]
CE_DRUH_POZEMKU_TBD (reader ORACLE_NONSPATIAL_1)
    attributes: ID number(10,0), SHORT_VALUE varchar2(30), VALUE varchar2(255), DATE_OF_CREATION date, DESIGNER varchar2(255), COMMENTARY varchar2(2000), ACTIVE number(1,0), PRIORITY number(10,0)
    -> FeatureMerger_3 [SUPPLIER]
OZ_MN_PROJEKT (reader ORACLE_NONSPATIAL_3)
    attributes: FID number(10,0), FID_PROJEKT number(10,0), FID_PARC number(10,0)
    -> ChangeDetector [ORIGINAL]
    -> AttributeKeeper
FeatureMerger
    ATTR_ACCUM_MODE = Merge Supplier
    ATTR_CONFLICT_RES = Use Requestor
    IGNORE_NULLS = No
    JOIN_KEYS = @Value(KatastrUzemi) @Value(ID) AUTO
    MERGE_TYPE = Attributes Only
    PROCESS_DUPS = NO
    REJECT_NULL_MISSING_KEYS = No
    SUPPLIERS_FIRST = No
    MERGED -> AttributeManager
    MERGED -> DuplicateFilter
AttributeManager
    ATTR_TABLE:
      SET_TO kmen_cislo = FME_CONDITIONAL:DEFAULT_VALUE'_FME_NO_OP_'BOOL_OP;OR;COMPOSITE_TEST;1;CASE_INSENSITIVE_TEST @Value(ParcCislo) CONTAINS /'@Left(@Value(ParcCislo),@FindString(@Value(ParcCislo),/,0,caseSensitive=TRUE))'BOOL_OP;OR;COMPOSITE_TEST;1;CASE_INSENSITIVE_TEST @Value(ParcCislo) NOT_CONTAINS /'@Value(ParcCislo)'FME_NUM_CONDITIONS3___
      SET_TO podlom_cislo = FME_CONDITIONAL:DEFAULT_VALUE''BOOL_OP;OR;COMPOSITE_TEST;1;CASE_INSENSITIVE_TEST @Value(ParcCislo) CONTAINS /'@Right(@Value(ParcCislo),@StringLength(@Value(ParcCislo))-@FindString(@Value(ParcCislo),/,0,caseSensitive=TRUE)-1)'FME_NUM_CONDITIONS2___
      SET_TO fidprojektprovazbu = @Value(FID)
    USER_EXPOSED_ATTRIBUTES = fidprojektprovazbu
    -> AttributeValueMapper
AttributeValueMapper
    LUT = Lesní pozemek,lesní pozemek,Manipulační plocha,ostatní plocha,Orná půda,orná půda,Ostatní plocha,ostatní plocha,Ovocný sad,ovocný sad,Parcela zjednodušené evidence,,Trvalý travní porost,trvalý travní porost,Vodní Plocha,vodní plocha,Vodní plocha,vodní plocha,Zastavěná plocha a nádvoří,zastavěná plocha a nádvoří,jiná plocha,ostatní plocha,manipulační plocha,ostatní plocha,obslužná komunikace,,ostatmí plocha,ostatní plocha,ostatní plocha,ostatní plocha,parcela zjednodušené evidence,,trvalý travnatý porost,trvalý travní porost,vodní plocha,vodní plocha,zastavěná plocha a nádvoří,zastavěná plocha a nádvoří,Chmelnice,chmelnice,FME_NULL_VALUE,,FVE,,PZE,,Střecha,,TTP,trvalý travní porost,Zahrada,zahrada,orna,orná půda,ostaní,ostatní plocha
    MAPPING_DIRECTION = FORWARD
    SRC = DruhPoz
    VAL_ATTR = _looked_up
    -> FeatureMerger_3 [REQUESTOR]
Note: Kontrola druhu pozemku a přiřazení ID_DRUH_POZEMKU
FeatureMerger_3
    ATTR_ACCUM_MODE = Prefix Supplier
    IGNORE_NULLS = No
    JOIN_KEYS = @Value(_looked_up) @Value(VALUE) AUTO
    MERGE_TYPE = Attributes Only
    PROCESS_DUPS = NO
    REJECT_NULL_MISSING_KEYS = No
    SUPPLIERS_FIRST = No
    SUPPLIER_PREFIX = R_
    MERGED -> FeatureMerger_2 [SUPPLIER]
AttributeManager_2
    ATTR_TABLE = SET_TO idfidprospojeni = @Value(FID)
    -> FeatureMerger_2 [REQUESTOR]
FeatureMerger_2
    ATTR_ACCUM_MODE = Merge Supplier
    ATTR_CONFLICT_RES = Use Supplier
    IGNORE_NULLS = No
    JOIN_KEYS = @Value(KATUZ_KOD) @Value(KU_KOD) AUTO @Value(KMENOVE_CISLO) @Value(kmen_cislo) AUTO @Value(PODDELENI_CISLA) @Value(podlom_cislo) AUTO @Value(DRUH_POZEMKU_KOD) @Value(R_ID) AUTO
    MERGE_TYPE = Attributes and Geometry
    PROCESS_DUPS = NO
    REJECT_NULL_MISSING_KEYS = No
    SUPPLIERS_FIRST = No
    MERGED -> AttributeManager_3
    UNUSED_SUPPLIER -> DateTimeStamper
AttributeManager_3
    ATTR_TABLE:
      REMOVE ID
      REMOVE ParcCislo
      REMOVE DruhPoz
      REMOVE CisloLV
      REMOVE KatastrUzemi
      REMOVE VymPoz
      REMOVE VyuzVymera
      REMOVE Vyneti
      REMOVE CenaVyneti
      REMOVE InfoVyneti
      REMOVE PopisUP
      REMOVE SouladUP
      REMOVE Transakce
      REMOVE PopisPoz
      REMOVE AktVyuz
      REMOVE VB_cizi
      REMOVE NameProjekt
      REMOVE OOCOZ
      REMOVE DateEvid
      REMOVE OwnerPoz
      REMOVE Smlouva
      REMOVE NOGODuvodSez
      REMOVE NOGODuvodText
      REMOVE PlochaBPEJ1
      REMOVE PlochaBPEJ2
      REMOVE PlochaBPEJ3
      REMOVE PlochaBPEJ4
      REMOVE PlochaBPEJ5
      REMOVE VymSluz
      REMOVE DelkaSluz
      REMOVE PopisSluz
      REMOVE kmen_cislo
      REMOVE podlom_cislo
      REMOVE KU_KOD
      REMOVE KU_NAZEV
      REMOVE datumdenminus
      REMOVE datummesicminus
      REMOVE FID
      REMOVE AREA
      REMOVE DATUM_UPRAV
      REMOVE DATUM_VYTVOR
      REMOVE ID_ACCESS
      REMOVE ID_PRIORITA
      REMOVE ID_STAV
      REMOVE ID_TYP
      REMOVE NAZEV
      REMOVE PLOCHA
      REMOVE PORAD_CISLO
      REMOVE POZNAMKA
      REMOVE SPP_PRVEK
      REMOVE USER_UPRAV
      REMOVE USER_VYTVOR
      REMOVE VYKON
      REMOVE OLD_FID
      RENAME_SET_VALUE fidprojektprovazbu > FID_PROJEKT
      REMOVE _looked_up
      REMOVE R_ID
      REMOVE R_SHORT_VALUE
      REMOVE R_VALUE
      REMOVE R_DATE_OF_CREATION
      REMOVE R_DESIGNER
      REMOVE R_COMMENTARY
      REMOVE R_ACTIVE
      REMOVE R_PRIORITY
      REMOVE DRUH_CISLOVANI_KOD
      REMOVE DRUH_POZEMKU_KOD
      REMOVE ID_TRANS_RUIAN
      REMOVE KATUZ_KOD
      REMOVE KMENOVE_CISLO
      REMOVE NESPRAVNY
      REMOVE PLATI_OD
      REMOVE PODDELENI_CISLA
      REMOVE RIZENI_ID
      REMOVE VYMERA_PARCELY
      REMOVE ZPUSOB_VYU_POZ_KOD
      REMOVE PUVOD
      REMOVE CIS_SML
      REMOVE FID_BUFFER
      REMOVE ID_KLASIFIKACE
      REMOVE DUVOD
      RENAME_SET_VALUE idfidprospojeni > FID_PARC
    -> ChangeDetector [REVISED]
ChangeDetector
    BLANK_AND_MISSING_DIFFER = No
    CHECK_TYPES_AND_ENCODINGS = No
    MATCHATTRS = FID_PARC FID_PROJEKT
    MATCH_STRATEGY = Match Selected Attributes
    UNCHANGED_OUTPUT = Output Original
    UPSERT_MODE = No
    INSERTED -> OZ_MN_PROJEKT (writer ORACLE_NONSPATIAL_2)
OZ_MN_PROJEKT (writer ORACLE_NONSPATIAL_2)
    attributes: FID_PROJEKT number(10,0), FID_PARC number(10,0)
DateTimeStamper
    DATETIME_ATTR = _timestamp
    INCLUDE_FRAC_SECONDS = YES
    STAMP_TYPE = date
    TIMEZONE = utc
    -> Sheet1 (writer XLSXW_2)
Sheet1 (writer XLSXW_2)
    attributes: ID number(20), ParcCislo string(20), DruhPoz string(255), CisloLV number(20), KatastrUzemi number(20), VymPoz number(20), VyuzVymera number(20), Vyneti boolean(20), CenaVyneti number(20), InfoVyneti string(50), PopisUP string(255), SouladUP boolean(20), Transakce string(40), PopisPoz string(20), AktVyuz string(255), VB_cizi string(255), NameProjekt number(20), OOCOZ number(20), DateEvid datetime(20), OwnerPoz string(20), Smlouva number(20), NOGODuvodSez number(20), NOGODuvodText string(20), PlochaBPEJ1 number(20), PlochaBPEJ2 number(20), PlochaBPEJ3 number(20), PlochaBPEJ4 number(20), PlochaBPEJ5 number(20), VymSluz number(20), DelkaSluz number(20),
      PopisSluz string(255), kmen_cislo string(200), podlom_cislo string(200), KU_KOD number(20), KU_NAZEV string(255), datumdenminus string(200), datummesicminus string(200), FID number(10), AREA number(20), DATUM_UPRAV datetime(20), DATUM_VYTVOR datetime(20), ID_ACCESS number(10), ID_PRIORITA number(10), ID_STAV number(10), ID_TYP number(10), NAZEV string(1020), PLOCHA number(10), PORAD_CISLO number(10), POZNAMKA string(1020), SPP_PRVEK string(1020), USER_UPRAV string(1020), USER_VYTVOR string(1020), VYKON number(10), OLD_FID number(10), fidprojektprovazbu string(200), _looked_up string(20), R_ID number(10), R_SHORT_VALUE string(30), R_VALUE string(255), R_DATE_OF_CREATION datetime(20),
      R_DESIGNER string(255), R_COMMENTARY string(2000), R_ACTIVE number(1), R_PRIORITY number(10), _timestamp string(20)

Bookmark: Dodatečné připojení parcel k projektům bez GEOM
AttributeKeeper
    CREATE_BULK_MODE_FEATURES = NO
    KEEP_ATTRS = FID_PROJEKT
    -> DuplicateFilter_2
DuplicateFilter_2
    INPUT_ORDERED_CHOICE = No
    KEYATTR = FID_PROJEKT
    UNIQUE -> FeatureJoiner_2 [LEFT]
FeatureJoiner_2
    ATTR_CONFLICT_RES = Prefer Left
    GEOMETRY_HANDLING = Prefer Left
    JOIN_KEYS = FID_PROJEKT FID AUTO
    JOIN_MODE = Inner
    UNJOINED_RIGHT -> FeatureMerger_4 [SUPPLIER]
FeatureMerger_4
    ATTR_ACCUM_MODE = Merge Supplier
    ATTR_CONFLICT_RES = Use Requestor
    IGNORE_NULLS = No
    JOIN_KEYS = @Value(NameProjekt) @Value(ID_ACCESS) AUTO
    MERGE_TYPE = Attributes Only
    PROCESS_DUPS = NO
    REJECT_NULL_MISSING_KEYS = No
    SUPPLIERS_FIRST = No
    MERGED -> FeatureMerger [REQUESTOR]

Bookmark: Download pozemku podle ku z MDB
Note: Jedinečné KU_KOD pro natažení pozemků z RUIANu
DuplicateFilter
    INPUT_ORDERED_CHOICE = No
    KEYATTR = KU_KOD
    UNIQUE -> FeatureReader [INITIATOR]
FeatureReader
    ATTRIBUTES = GISOZETB.OZ_PARC,"FID,AREA,CIS_SML,DRUH_CISLOVANI_KOD,DRUH_POZEMKU_KOD,DUVOD,FID_BUFFER,ID,ID_KLASIFIKACE,ID_STAV,KATUZ_KOD,KMENOVE_CISLO,NESPRAVNY,PLATI_OD,PODDELENI_CISLA,POZNAMKA,PUVOD,RIZENI_ID,VYMERA_PARCELY,ZPUSOB_VYU_POZ_KOD,ID_TRANS_RUIAN"
    ATTR_ACCUM_MODE = Only Use Result
    COMBINE_GEOM = Use Result
    DATASET = vyrokt_GISOZETB
    FEATURETYPES = GISOZETB.OZ_PARC
    FORMAT = ORACLE_SPATIAL
    INTERACT = NONE
    ORACLE_SPATIAL_CHUNK_SIZE = 200
    ORACLE_SPATIAL_CREATE_FEATURE_TABLES_FROM_DATA = Yes
    ORACLE_SPATIAL_HANDLE_MULTIPLE_SPATIAL_COLUMNS = NO
    ORACLE_SPATIAL_NAMED_CONNECTION = vyrokp_GISOZETB
    ORACLE_SPATIAL_PARSE_MAPINFO_SYMBOLOGY = NO
    ORACLE_SPATIAL_PERSISTENT_CONNECTION = YES
    ORACLE_SPATIAL_QUERY_FEATURE_TYPES_FOR_MERGE_FILTERS = Yes
    ORACLE_SPATIAL_READ_3D_POLYGON_AS_FACE = NO
    ORACLE_SPATIAL_REMOVE_SCHEMA_QUALIFIER = NO
    ORACLE_SPATIAL_SERVER_TYPE = ORACLE8i
    ORACLE_SPATIAL_SHOW_SYSTEM_TABLES = NO
    ORACLE_SPATIAL_USE_SEARCH_ENVELOPE = NO
    ORACLE_SPATIAL_USE_UNIFIED_DATE_ATTRS = YES
    OUTPUT_FEATURES_DISPLAY = Schema and Data Features
    WHERE = "KATUZ_KOD" = @Value(KU_KOD)
    GISOZETB.OZ_PARC -> AttributeManager_2

FME custom transformer NoFeaturesTester
Description
This transformer checks whether there are any input features. If not, then a single feature is ouput via the NOINPUT port. If INPUT features exist, then they are output via the INPUT output port.
Other transformers often generate features that signify an error condition. This transformer can be used to check for those features and if those features exists, then a separate action can be triggered.
Example 
This may be useful to test if any data emerges from a reader, when the 'Ignore Failed Readers' advanced parameter is set to yes.
Input Ports 
Input: Features to be checked for existence. Any features will be accepted. 
Output Ports
NoInput:
If no input features exist, a single featue is returned via the NoInput port. 
Output: 
Any feature that entered the Input port is returned via the Output port.

INPUT (input)
    -> Sampler
    -> OUTPUT (output)
OUTPUT (output)
Sampler
    RATE = 1
    SAMPLE_MODE = No
    SAMPLE_TYPE_LONG = First N Features
    SAMPLED -> AttributeCreator_2
AttributeCreator_2
    ATTR_TABLE:
      SET_TO count = 0
      SET_TO remove = yes
    -> DuplicateFilter
Creator
    GEOMTYPE = Geometry Object
    NUM = 1
    CREATED -> AttributeCreator_3
AttributeCreator_3
    ATTR_TABLE = SET_TO no_features = true
    -> DuplicateFilter
DuplicateFilter
    INPUT_ORDERED_CHOICE = No
    KEYATTR = count
    UNIQUE -> Tester
Tester
    BOOL_OP = OR
    TEST_CLAUSE = TEST @Value(remove) != yes
    TEST_MODE = TEST
    PASSED -> AttributeRemover
AttributeRemover
    REMOVE_ATTRS = count,remove
    -> NOINPUT (output)
NOINPUT (output)
