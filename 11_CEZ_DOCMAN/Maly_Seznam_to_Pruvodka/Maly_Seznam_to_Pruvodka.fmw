FME workspace Maly_Seznam_to_Pruvodka.fmw

Parameters:
- Slozka = ETU/ETU_0876_JMA   # Slozka se souborem
- KPJM = zdeborjan   # Zadajte KPJM
- API_PARAM_P_T = https://restapidv2.cezdata.corp/esb/ecm/document/v1/get-property-values/   # Produkce/Test
- Pevna_cesta = \\dfs03.cezdata.corp\CEZ\DKE\9050060_ŘTKE\TPKE\RIZEK\JMA do DOCMAN\
- FME_JOB_ID = 1   # FME Flow Job ID

Note: TestFilter_3 : Input
Junction_7
    -> Junction_8
Note: AttributeRemover_2 : Output
Note: Pozor na Test vs Produkce přepínač
Junction_8
    -> Junction_5
    -> Sampler
Note: AttributeKeeper_9 : Output
Junction_14
    -> Sorter
StringReplacer
    CASE = NO
    FIND_TEXT = /
    NO_MATCH = _FME_NO_OP_
    REGEXP = NO
    REPLACE_TEXT = \
    SRC_ATTRS = FileNetPath,PathToFiles
    -> FeatureMerger_11 [REQUESTOR]
Note: AttributeKeeper_4 : Output
Junction_3
    -> Sorter
Sorter
    SORT_PARM = Cislo radku NATURAL ASCENDING
    SORTED -> AttributeManager_18
    SORTED -> FeatureMerger_11 [SUPPLIER]
FeatureMerger_11
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = 1 1 AUTO
    MERGE_TYPE = Attributes Only
    PROCESS_DUPS = YES
    REJECT_NULL_MISSING_KEYS = No
    SUPPLIERS_FIRST = No
    UNMERGED_REQUESTOR -> AttributeManager_19

Bookmark: Číselník Docman - RestAPI
Creator_2
    GEOMTYPE = Geometry Object
    NUM = 1
    CREATED -> HTTPCaller
HTTPCaller
    ADDITIONAL_URL_PARAMETERS = DomainName;%
    AUTH_METHOD = Basic
    AUTH_PASSWORD =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
    AUTH_USERNAME = qpfmeserver
    CONNECTION_TIMEOUT_LENGTH = 60
    CUSTOM_HEADERS = messageId;$(FME_JOB_ID) timestamp;@DateTimeNow() sourceSystem;FME Server
    ERROR_ATTR = _error
    FOLLOW_REDIRECTS = FOLLOW_WITH_GET
    HTTP_METHOD = GET
    MAX_HTTP_VERSION = HTTP_1_1
    MAX_TRANSFERS_IN_PROGRESS = 10
    MINIMUM_ENCRYPTION_LEVEL = OS_DEFAULT
    MULTIPART_RESPONSE_HEADER_LIST_ATTR = _multipart_headers
    REDIRECT_AUTH = ORIGINAL_DOMAIN_ONLY
    RESPONSE_TYPE = Attribute
    SPLIT_MULTIPART_DOWNLOADS = YES
    TARGET_ATTR = _response_body
    TARGET_ATTR_ENCODING = fme-system
    TARGET_URL = $(API_PARAM_P_T)
    TRANSFER_TIMEOUT_LENGTH = 90
    USE_COOKIES = No
    VERIFY_SSL_CERTIFICATES = No
    -> AttributeCreator_4
AttributeCreator_4
    ATTR_TABLE = SET_TO _response_body = {"features":@Value(_response_body)}
    -> JSONFragmenter_2
JSONFragmenter_2
    EXPLODE_FORMAT = JSON
    EXTRACT_ATTR = Yes
    JSON_ATTR = _response_body
    JSON_QUERY = json["features"][*]
    READ_FROM_FILE = NO
    RECURSIVE = Yes
    REJECT_EMPTY_LISTS = YES
    FRAGMENTS -> AttributeExposer_3
AttributeExposer_3
    ATTR_LIST = value,domainName,description
    -> AttributeKeeper_7
AttributeKeeper_7
    CREATE_BULK_MODE_FEATURES = NO
    KEEP_ATTRS = description,domainName,value
    -> TestFilter_5
TestFilter_5
    DEFAULT_VALUE = <UNFILTERED>
    PASSED_TEST_GROUP_OUTPUT = FIRST
    TEST_LIST = "BOOL_OP,OR,COMPOSITE_TEST,""""""1"""""",TEST_CLAUSE,TEST @Value(domainName) = CompanyIssuing",CompanyIssuing,"BOOL_OP,OR,COMPOSITE_TEST,""""""1"""""",TEST_CLAUSE,TEST @Value(domainName) = DocumentSubType",DocumentSubType,"BOOL_OP,OR,COMPOSITE_TEST,""""""1"""""",TEST_CLAUSE,TEST @Value(domainName) = DocumentType",DocumentType,"BOOL_OP,OR,COMPOSITE_TEST,""""""1"""""",TEST_CLAUSE,TEST @Value(domainName) = SegmentationaccordingtoCSNEN6135A1",SegmentationaccordingtoCSNEN6135A1,"BOOL_OP,OR,COMPOSITE_TEST,""""""1"""""",TEST_CLAUSE,TEST @Value(domainName) = SegmentationaccordingtoCSNEN6135A3",SegmentationaccordingtoCSNEN6135A3
    CompanyIssuing -> Test_ciselniku_Company_Issuing_2 [SUPPLIER]
    DocumentSubType -> Test_ciselniku_Doc_SubType [SUPPLIER]
    DocumentType -> Test_ciselniku_Doc_Type [SUPPLIER]
    SegmentationaccordingtoCSNEN6135A1 -> Test_ciselniku_DCC_A1 [SUPPLIER]
    SegmentationaccordingtoCSNEN6135A3 -> Test_ciselniku_DCC_A2A3_2 [SUPPLIER]

Bookmark: Načtení dat
Creator
    GEOMTYPE = Geometry Object
    NUM = 1
    CREATED -> AttributeManager_14
AttributeManager_14
    ATTR_TABLE:
      SET_TO A (varchar(200)) = $(Pevna_cesta)
      SET_TO B (varchar(200)) = $(Slozka)
    -> FeatureReader_2 [INITIATOR]
Note: Vylistuje soubor "Seznam dokumentace*.xlsm" v kombinaci pevně dané cesty a uživatelsky dodaném názvu složky
FeatureReader_2
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    COMBINE_GEOM = Use Result
    DATASET = @Value(A)\@Value(B)
    FORMAT = PATH
    OUTPUT_FEATURES_DISPLAY = Schema and Data Features
    PATH_HIDDEN_FILES = INCLUDE
    PATH_NO_EMPTY_PROPERTIES = YES
    PATH_OFFSET_DATETIME = yes
    PATH_RECURSE_DIRECTORIES = NO
    PATH_RETRIEVE_FILE_PROPERTIES = YES
    PATH_TYPE = FILE
    PATH_USE_NON_STRING_ATTR = yes
    PATH -> TestFilter_7
TestFilter_7
    DEFAULT_VALUE = <UNFILTERED>
    PASSED_TEST_GROUP_OUTPUT = FIRST
    TEST_LIST = "BOOL_OP,OR,COMPOSITE_TEST,""""""1"""""",TEST_CLAUSE,CASE_INSENSITIVE_TEST @Value(path_filename) CONTAINS_REGEX ^SEZNAM DOKUMENTACE.*(?i)xlsm$",Seznam - zpracovat,"BOOL_OP,OR,COMPOSITE_TEST,""""""1"""""",TEST_CLAUSE,CASE_SENSITIVE_TEST @Value(path_filename) CONTAINS_REGEX (^Report)|(^transmittal_sheet)",Report/transmital_sheet - smazat
    Seznam - zpracovat -> FeatureHolderExt [Keep]
    Report/transmital_sheet - smazat -> FileDeleter
FileDeleter
    FileToDelete = @Value(path_windows)
    -> FeatureHolderExt [Discard]
FeatureHolderExt
    Kept -> AttributeManager_6
AttributeManager_6
    ATTR_TABLE:
      RENAME_SET_VALUE path_windows > Cesta k Seznamu
      RENAME_SET_VALUE path_directory_windows > Cesta ke slozce Seznamu
      RENAME_SET_VALUE path_rootname > Název Seznamu bez prip
      RENAME_SET_VALUE path_filename > Název Seznamu
      REMOVE path_unix
      REMOVE path_extension
      REMOVE path_filesize
      REMOVE path_ownername
      REMOVE path_readonly
      REMOVE path_modified_date
      REMOVE path_created_date
      REMOVE path_accessed_date
      REMOVE path_directory_unix
      REMOVE path_type
      REMOVE fme_geometry{0}
      REMOVE fme_geometry{}
    -> FeatureReader_3 [INITIATOR]
Note: Načte Data z excelu
FeatureReader_3
    ATTR_ACCUM_MODE = Merge Initiator and Result
    ATTR_CONFLICT_RES = Use Result
    ATTR_IGNORE_NULLS = No
    COMBINE_GEOM = Use Result
    DATASET = @Value(Cesta k Seznamu)
    FORMAT = XLSXR
    INTERACT = NONE
    ORDER_RESULTS = No
    OUTPUT_FEATURES_DISPLAY = Schema and Data Features
    XLSXR_ALLOW_DOLLAR_SIGNS = YES
    XLSXR_APPLY_FILTERS = No
    XLSXR_CASE_SENSITIVE_FEATURE_TYPES = YES
    XLSXR_CREATE_FEATURE_TABLES_FROM_DATA = Yes
    XLSXR_EXCEL_COL_NAMES = YES
    XLSXR_EXPAND_MERGED_CELLS = Yes
    XLSXR_FORCE_DATETIME = NO
    XLSXR_QUERY_FEATURE_TYPES_FOR_MERGE_FILTERS = Yes
    XLSXR_READ_BLANK_AS = Missing
    XLSXR_READ_FORM_CONTROLS = NONE
    XLSXR_READ_RASTER_MODE = None
    XLSXR_REPLACE_ONLY_NEWLINES_CARRIAGE_RETURNS = YES
    XLSXR_SCAN_MAX_FEATURES = 1000
    XLSXR_SCHEMA_HANDLING_REVISION = 2
    XLSXR_SKIP_EMPTY_ROWS = YES
    XLSXR_STRIP_SHEETNAME_SPACES = YES
    XLSXR_TRIM_ATTR_NAME_WHITESPACE = Yes
    XLSXR_USE_CUSTOM_SCHEMA = NO
    <SCHEMA> -> TestFilter_6
    <OTHER> -> AttributeExposer_2
AttributeExposer_2
    ATTR_LIST = A,B,C,D,E,F,G,H,I,J,K,L,N,P,fme_feature_type,xlsx_row_id,Q
    -> TestFilter_4
Note: Filtruje listy, projde jen co obsahuje Seznam*
TestFilter_4
    DEFAULT_VALUE = <UNFILTERED>
    PASSED_TEST_GROUP_OUTPUT = FIRST
    TEST_LIST = "BOOL_OP,OR,COMPOSITE_TEST,""""""1"""""",TEST_CLAUSE,CASE_INSENSITIVE_TEST @Value(fme_feature_type) CONTAINS SEZNAM",@Value(fme_feature_type) CONTAINS SEZNAM
    @Value(fme_feature_type) CONTAINS SEZNAM -> TestFilter_8

Bookmark: Mapování atributů
TestFilter_8
    DEFAULT_VALUE = Garbage
    PASSED_TEST_GROUP_OUTPUT = FIRST
    TEST_LIST = "BOOL_OP,OR,COMPOSITE_TEST,""""""1"""""",TEST_CLAUSE,TEST @Value(xlsx_row_id) = 3",Header,"BOOL_OP,OR,COMPOSITE_TEST,""""""1"""""",TEST_CLAUSE,TEST @Value(xlsx_row_id) >= 7",Datas
    Header -> AttributeManager_16
    Datas -> AttributeManager_17
AttributeManager_16
    ATTR_TABLE:
      RENAME_SET_VALUE A > Typ akce (varchar(200))
      RENAME_SET_VALUE B > Kod projektu (varchar(200))
      REMOVE C (varchar(200))
      REMOVE D (varchar(200))
      REMOVE E (varchar(200))
      REMOVE F (varchar(200))
      RENAME_SET_VALUE G > Popis akce (varchar(200))
      REMOVE H (varchar(200))
      RENAME_SET_VALUE I > Elektrarna (varchar(200))
      REMOVE J (varchar(200))
      REMOVE K (varchar(200))
      REMOVE L (varchar(200))
      REMOVE N (varchar(200))
      RENAME_SET_VALUE P > Zhotovitel (varchar(200))
      REMOVE Q (varchar(200))
    -> FeatureMerger_12 [SUPPLIER]
AttributeManager_17
    ATTR_TABLE:
      REMOVE A (varchar(200))
      RENAME_SET_VALUE B > Cislo SO (varchar(200))
      RENAME_SET_VALUE C > Oznaceni PS/DPS (varchar(200))
      RENAME_SET_VALUE D > Typ dokumentu (varchar(200))
      RENAME_SET_VALUE E > Podtyp dokumentu (varchar(200))
      RENAME_SET_VALUE F > DCC A1 (varchar(200))
      RENAME_SET_VALUE G > Nazev dokumentu (varchar(200))
      RENAME_SET_VALUE H > Doplnujici nazev predmetu, umisteni (varchar(200))
      RENAME_SET_VALUE I > Projekcni oznaceni (KKS) (varchar(200))
      RENAME_SET_VALUE J > Archivni cislo dokumentu / Nazev souboru (varchar(200))
      RENAME_SET_VALUE K > Pocet listu v dokumentu (varchar(200))
      RENAME_SET_VALUE L > Revize dokumentu (varchar(200))
      RENAME_SET_VALUE N > Cesta elektronickeho souboru (varchar(200))
      RENAME_SET_VALUE P > Datum vytvoreni (varchar(200))
      RENAME_SET_VALUE Q > Podslozka (varchar(200))
    -> FeatureMerger_12 [REQUESTOR]
FeatureMerger_12
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Odstrani_tab

Bookmark: Předúprava atributů - odstranení nev. znaků
Odstrani_tab: StringReplacer
    CASE = NO
    FIND_TEXT = "\n"
    NO_MATCH = _FME_NO_OP_
    REGEXP = NO
    SRC_ATTRS = xlsx_row_id,fme_feature_type,Archivni cislo dokumentu / Nazev souboru,Cesta elektronickeho souboru,Cesta k Seznamu,Cesta ke slozce Seznamu,Cislo SO,Datum vytvoreni,DCC A1,Doplnujici nazev predmetu, umisteni,Elektrarna,Kod projektu,Nazev dokumentu,Název Seznamu,Název Seznamu bez prip,Oznaceni PS/DPS,Pocet listu v dokumentu,Podslozka,Podtyp dokumentu,Popis akce,Projekcni oznaceni (KKS),Revize dokumentu,Typ akce,Typ dokumentu,Zhotovitel
    -> Odstrani_enter
Odstrani_enter: StringReplacer
    CASE = NO
    FIND_TEXT = "    "
    NO_MATCH = _FME_NO_OP_
    REGEXP = NO
    SRC_ATTRS = fme_feature_type,xlsx_row_id,Archivni cislo dokumentu / Nazev souboru,Cesta elektronickeho souboru,Cesta k Seznamu,Cesta ke slozce Seznamu,Cislo SO,Datum vytvoreni,DCC A1,Doplnujici nazev predmetu, umisteni,Elektrarna,Kod projektu,Nazev dokumentu,Název Seznamu,Název Seznamu bez prip,Oznaceni PS/DPS,Pocet listu v dokumentu,Podslozka,Podtyp dokumentu,Popis akce,Projekcni oznaceni (KKS),Revize dokumentu,Typ akce,Typ dokumentu,Zhotovitel
    -> AttributeTrimmer
AttributeTrimmer
    SRC_ATTRS = fme_feature_type,xlsx_row_id,"Archivni cislo dokumentu / Nazev souboru","Cesta elektronickeho souboru","Cesta k Seznamu","Cesta ke slozce Seznamu","Cislo SO","Datum vytvoreni","DCC A1","Doplnujici nazev predmetu, umisteni",Elektrarna,"Kod projektu","Nazev dokumentu","Název Seznamu","Název Seznamu bez prip","Oznaceni PS/DPS","Pocet listu v dokumentu",Podslozka,"Podtyp dokumentu","Popis akce","Projekcni oznaceni (KKS)","Revize dokumentu","Typ akce","Typ dokumentu",Zhotovitel
    TRIM_TO_NONE = Yes
    TRIM_TYPE = Both
    -> Zmena_nazvu_slozek_Filesystem

Bookmark: Dlouhé názvy složek na krátké
Zmena_nazvu_slozek_Filesystem: PythonCaller
    PYTHONSOURCE:
      import os
      import sys
      import fme
      import fmeobjects


      class FolderNameChanger(object):
          """Template Class Interface:
          When using this class, make sure its name is set as the value of the 'Class
          to Process Features' transformer parameter.
          """

          def __init__(self):

              LookUp_Table = {"02 - Dokumenty managementu - Ostatní":"Ost", "03 - Projektová dokumentace (PD)":"PD", "04 - Technická dokumentace (TD)":"TD", "05 - Průvodní technická dokumentace (PTD)":"PTD", "06 - Dokumentace skutečného stavu (As Built)":"DSS"}

              Pevna_cesta = FME_MacroValues['Pevna_cesta']
              Slozka = FME_MacroValues['Slozka']
              Cesta_ke_slozce_Seznamu = Pevna_cesta + '\\' + Slozka

              #Dodělat TryCatch a RejectedPort

              for key in LookUp_Table:
                  Folder_old = Cesta_ke_slozce_Seznamu+ '\\' +key
                  Folder_new = Cesta_ke_slozce_Seznamu+ '\\' +LookUp_Table[key]
                  if os.path.exists(Folder_old):
                      os.rename(Folder_old, Folder_new)

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """

              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FolderNameChanger
    -> Změna_nazvu_slozek_FME
Změna_nazvu_slozek_FME: StringPairReplacer
    CASE = no
    MAP = 02\ -\ Dokumenty\ managementu\ -\ Ostatní Ost 03\ -\ Projektová\ dokumentace\ (PD) PD 04\ -\ Technická\ dokumentace\ (TD) TD 05\ -\ Průvodní\ technická\ dokumentace\ (PTD) PTD 06\ -\ Dokumentace\ skutečného\ stavu\ (As\ Built) DSS
    SRC_ATTRS = Cesta elektronickeho souboru
    -> AttributeValidator_2

Bookmark: Kontrola vyplnění povinných atributů v hlavičce
AttributeValidator_2
    TABLE = Elektrarna,Kod projektu,Popis akce,Typ akce,Zhotovitel;ATTRIBUTE_HAS_A_VALUE;<Unused>
    PASSED -> Test_ciselniku_Company_Issuing_2 [REQUESTOR]
    FAILED -> Sampler_3
Sampler_3
    RATE = 1
    SAMPLE_MODE = No
    SAMPLE_TYPE_LONG = First N Features
    SAMPLED -> ListConcatenator_3
ListConcatenator_3
    DROP_EMPTY_PARTS = No
    LIST_ATTR = _fme_validation_message_list{}
    SEP = ,
    VAL_ATTR = _concatenated
    -> TestFilter_9
Note: Chyba = konec
TestFilter_9
    DEFAULT_VALUE = <UNFILTERED>
    PASSED_TEST_GROUP_OUTPUT = ALL
    TEST_LIST = "BOOL_OP,OR,COMPOSITE_TEST,""""""1"""""",TEST_CLAUSE,CASE_INSENSITIVE_TEST @Value(_concatenated) CONTAINS Elektrarna",Elektrarna chybi,"BOOL_OP,OR,COMPOSITE_TEST,""""""1"""""",TEST_CLAUSE,CASE_INSENSITIVE_TEST @Value(_concatenated) CONTAINS Popis akce",Popis akce chybi,"BOOL_OP,OR,COMPOSITE_TEST,""""""1"""""",TEST_CLAUSE,CASE_INSENSITIVE_TEST @Value(_concatenated) CONTAINS Kod projektu",Kod projektu chybi,"BOOL_OP,OR,COMPOSITE_TEST,""""""1"""""",TEST_CLAUSE,CASE_INSENSITIVE_TEST @Value(_concatenated) CONTAINS Typ akce",Typ akce chybi,"BOOL_OP,OR,COMPOSITE_TEST,""""""1"""""",TEST_CLAUSE,CASE_INSENSITIVE_TEST @Value(_concatenated) CONTAINS Zhotovitel",Zhotovitel chybi
    Elektrarna chybi -> Popis_chyby_Elektrarna
    Popis akce chybi -> Popis_chyby_Popis_akce
    Kod projektu chybi -> Popis_chyby_Kod_projektu
    Typ akce chybi -> Popis_chyby_Typ_akce
    Zhotovitel chybi -> Popis_chyby_Zhotovitel
Popis_chyby_Typ_akce: AttributeCreator
    ATTR_TABLE:
      SET_TO Atribut = Typ akce
      SET_TO Hodnota atributu = Nezadáno
      SET_TO Popis chyby = Chyba hlavičky, hodnota nezadána
    -> AttributeManager_2
Popis_chyby_Popis_akce: AttributeCreator
    ATTR_TABLE:
      SET_TO Atribut = Popis akce
      SET_TO Hodnota atributu = Nezadáno
      SET_TO Popis chyby = Chyba hlavičky, hodnota nezadána
    -> AttributeManager_2
Popis_chyby_Kod_projektu: AttributeCreator
    ATTR_TABLE:
      SET_TO Atribut = Kód projektu
      SET_TO Hodnota atributu = Nezadáno
      SET_TO Popis chyby = Chyba hlavičky, hodnota nezadána
    -> AttributeManager_2
Popis_chyby_Elektrarna: AttributeCreator
    ATTR_TABLE:
      SET_TO Atribut = Elektrarna
      SET_TO Hodnota atributu = Nezadáno
      SET_TO Popis chyby = Chyba hlavičky, hodnota nezadána
    -> AttributeManager_2
Popis_chyby_Zhotovitel: AttributeCreator
    ATTR_TABLE:
      SET_TO Atribut = Zhotovitel
      SET_TO Hodnota atributu = Nezadáno
      SET_TO Popis chyby = Chyba hlavičky, hodnota nezadána
    -> AttributeManager_2
AttributeManager_2
    ATTR_TABLE:
      RENAME_SET_VALUE Cesta k Seznamu > Cesta elektronickeho souboru
      RENAME_SET_VALUE Název Seznamu > FileName
      RENAME_SET_VALUE xlsx_row_id > Cislo radku
      SET_TO Sheet_name = Chyby v Seznamu dokumentace
    -> AttributeKeeper_4
AttributeKeeper_4
    CREATE_BULK_MODE_FEATURES = NO
    KEEP_ATTRS = Atribut,Cesta elektronickeho souboru,FileName,Hodnota atributu,Popis chyby,Cislo radku,Sheet_name
    -> Junction_2
Note: Sorter : Input
Junction_2
    -> Junction_3

Bookmark: Kontrola hlavičky na číselník
Test_ciselniku_Company_Issuing_2: FeatureMerger
    ATTR_ACCUM_MODE = Merge Supplier
    ATTR_CONFLICT_RES = Use Requestor
    IGNORE_NULLS = No
    JOIN_KEYS = @Value(Zhotovitel) @Value(value) AUTO
    MERGE_TYPE = Attributes Only
    PROCESS_DUPS = NO
    REJECT_NULL_MISSING_KEYS = No
    SUPPLIERS_FIRST = No
    MERGED -> AttributeRemover_2
    UNMERGED_REQUESTOR -> Sampler_4
AttributeRemover_2
    REMOVE_ATTRS = description,domainName,value
    -> AttributeValidator
Sampler_4
    RATE = 1
    SAMPLE_MODE = No
    SAMPLE_TYPE_LONG = First N Features
    SAMPLED -> AttributeManager_7
Note: Chyba = konec
AttributeManager_7
    ATTR_TABLE:
      SET_TO Atribut = Zhotovitel
      SET_TO Hodnota atributu = @Value(Zhotovitel)
      SET_TO Popis chyby = Zadaný zhotovitel není v číselníku
      SET_TO Sheet_name = Chyby v Seznamu dokumentace
      RENAME_SET_VALUE Cesta k Seznamu > Cesta elektronickeho souboru
      RENAME_SET_VALUE Název Seznamu > FileName
      RENAME_SET_VALUE xlsx_row_id > Cislo radku
      REMOVE Cesta ke slozce Seznamu
      REMOVE Název Seznamu bez prip
      REMOVE fme_feature_type
      REMOVE Cislo SO
      REMOVE Oznaceni PS/DPS
      REMOVE Typ dokumentu
      REMOVE Podtyp dokumentu
      REMOVE DCC A1
      REMOVE Nazev dokumentu
      REMOVE Doplnujici nazev predmetu, umisteni
      REMOVE Projekcni oznaceni (KKS)
      REMOVE Archivni cislo dokumentu / Nazev souboru
      REMOVE Pocet listu v dokumentu
      REMOVE Revize dokumentu
      REMOVE Cesta elektronickeho souboru
      REMOVE Datum vytvoreni
      REMOVE Podslozka
      REMOVE Typ akce
      REMOVE Kod projektu
      REMOVE Popis akce
      REMOVE Elektrarna
      REMOVE Zhotovitel
    -> Sorter

Bookmark: Kontrola vyplnění povinných dat
AttributeValidator
    TABLE = Archivni cislo dokumentu / Nazev souboru,Cesta elektronickeho souboru,Cislo SO,Datum vytvoreni,DCC A1,Doplnujici nazev predmetu, umisteni,Kod projektu,Nazev dokumentu,Oznaceni PS/DPS,Pocet listu v dokumentu,Podslozka,Podtyp dokumentu,Projekcni oznaceni (KKS),Revize dokumentu;CONTAINS_REGEX;^[^~]*$/Archivni cislo dokumentu / Nazev souboru,Cesta elektronickeho souboru,Cislo SO,Datum vytvoreni,DCC A1,Doplnujici nazev predmetu, umisteni,Kod projektu,Nazev dokumentu,Oznaceni PS/DPS,Pocet listu v dokumentu,Podslozka,Podtyp dokumentu,Projekcni oznaceni (KKS),Revize dokumentu;CONTAINS_REGEX;^[^;]*$
    PASSED -> Junction_7
    FAILED -> ListExploder
    FAILED -> FeatureMerger [SUPPLIER]
Note: ListExploder / An attribute may fail multiple tests / Split the list to create one record per test message
ListExploder
    ATTR_ACCUM_MODE = Merge List Attributes
    ATTR_CONFLICT_RES = Use List Attribute Values
    INDEX_ATTR = _element_index
    LIST_ATTR = _fme_validation_message_list{}
    ELEMENTS -> AttributeExploder
Note: AttributeExploder / Create a set of name/value pairs : for each test
AttributeExploder
    ATTR_NAME_LABEL = _attr_name
    ATTR_VALUE_LABEL = _attr_value
    EXPLODING_TYPE = Features
    KEEP_ATTRIBUTES = Yes
    KEEP_GEOMETRY = No
    -> StringSearcher
Note: StringSearcher / Find name/value pairs that have an error message
StringSearcher
    CASE = no
    MATCHED_RESULT_ATTR = _first_match
    REGEXP = '@Value(_attr_name)'
    STRING_TO_SEARCH = @Value(_fme_validation_message_list)
    MATCHED -> TestFilter_2
TestFilter_2
    DEFAULT_VALUE = <UNFILTERED>
    PASSED_TEST_GROUP_OUTPUT = FIRST
    TEST_LIST = "BOOL_OP,OR,COMPOSITE_TEST,""""""1"""""",TEST_CLAUSE,CASE_SENSITIVE_TEST @Value(_fme_validation_message_list) CONTAINS ^[^~]*$'",~,"BOOL_OP,OR,COMPOSITE_TEST,""""""1"""""",TEST_CLAUSE,CASE_SENSITIVE_TEST @Value(_fme_validation_message_list) CONTAINS ^[^;]*$'",;
    ~ -> AttributeCreator
    ; -> AttributeCreator_2
AttributeCreator
    ATTR_TABLE = SET_TO Znak (buffer) = ~
    -> AttributeManager_15
Note: Chyba = odstranění feature
AttributeCreator_2
    ATTR_TABLE = SET_TO Znak (buffer) = ;
    -> AttributeManager_15
AttributeManager_15
    ATTR_TABLE:
      SET_TO Atribut = @Value(_attr_name)
      SET_TO Hodnota atributu = @Value(@Value(_attr_name))
      SET_TO Popis chyby = Atribut "@Value(_attr_name)" obsahuje nepovolený znak -> "@Value(Znak)" <-
      SET_TO Sheet_name = Chyby v Seznamu dokumentace
      RENAME_SET_VALUE Cesta k Seznamu > Cesta elektronickeho souboru
      RENAME_SET_VALUE Název Seznamu > FileName
      RENAME_SET_VALUE xlsx_row_id > Cislo radku
      REMOVE Cesta ke slozce Seznamu
      REMOVE Název Seznamu bez prip
      REMOVE fme_feature_type
      REMOVE Cislo SO
      REMOVE Oznaceni PS/DPS
      REMOVE Typ dokumentu
      REMOVE Podtyp dokumentu
      REMOVE DCC A1
      REMOVE Nazev dokumentu
      REMOVE Doplnujici nazev predmetu, umisteni
      REMOVE Projekcni oznaceni (KKS)
      REMOVE Archivni cislo dokumentu / Nazev souboru
      REMOVE Pocet listu v dokumentu
      REMOVE Revize dokumentu
      REMOVE Cesta elektronickeho souboru
      REMOVE Datum vytvoreni
      REMOVE Podslozka
      REMOVE Typ akce
      REMOVE Kod projektu
      REMOVE Popis akce
      REMOVE Elektrarna
      REMOVE Zhotovitel
      REMOVE _fme_validation_message
      REMOVE _fme_validation_message_list
      REMOVE _element_index
      REMOVE _attr_name
      REMOVE _attr_value
      REMOVE _first_match
      REMOVE Znak
    -> Sorter

Bookmark: Příprava na kontrolu, zda jsou soubory opravdu ve složce dle Průvodky
Sampler
    RATE = 1
    SAMPLE_MODE = No
    SAMPLE_TYPE_LONG = First N Features
    SAMPLED -> FeatureReader [INITIATOR]
FeatureReader
    ATTR_ACCUM_MODE = Only Use Result
    COMBINE_GEOM = Use Initiator
    DATASET = @Substring(@Value(Cesta k Seznamu),0,@FindRegularExpression(@Value(Cesta k Seznamu),(\\)(?!.*\\),0,0,0,caseSensitive=TRUE))
    FORMAT = PATH
    ORDER_RESULTS = No
    OUTPUT_FEATURES_DISPLAY = Data Features
    PATH_GLOB_PATTERN = *
    PATH_NO_EMPTY_PROPERTIES = YES
    PATH_OFFSET_DATETIME = yes
    PATH_RECURSE_DIRECTORIES = YES
    PATH_RETRIEVE_FILE_PROPERTIES = NO
    PATH_TYPE = FILE
    PATH_USE_NON_STRING_ATTR = yes
    <OTHER> -> AttributeExposer
AttributeExposer
    ATTR_LIST = path_windows,path_directory_windows
    -> TestFilter
TestFilter
    DEFAULT_VALUE = Nezájmové soubory
    PASSED_TEST_GROUP_OUTPUT = FIRST
    TEST_LIST:
      "BOOL_OP,OR,COMPOSITE_TEST,""""""1 OR 2"""""",TEST_CLAUSE,CASE_INSENSITIVE_TEST @Value(path_windows) CONTAINS \02 - Dokumenty managementu - Ostatní\
      CASE_INSENSITIVE_TEST @Value(path_windows) CONTAINS \Ost\",02 - Dokumenty managementu - Ostatn,"BOOL_OP,OR,COMPOSITE_TEST,""""""1 OR 2"""""",TEST_CLAUSE,CASE_INSENSITIVE_TEST @Value(path_windows) CONTAINS \03 - Projektová dokumentace (PD)\
      CASE_INSENSITIVE_TEST @Value(path_windows) CONTAINS \PD\",03 - Projektová dokumentace (PD),"BOOL_OP,OR,COMPOSITE_TEST,""""""1 OR 2"""""",TEST_CLAUSE,CASE_INSENSITIVE_TEST @Value(path_windows) CONTAINS \04 - Technická dokumentace (TD)\
      CASE_INSENSITIVE_TEST @Value(path_windows) CONTAINS \TD\",04 - Technická dokumentace (TD),"BOOL_OP,OR,COMPOSITE_TEST,""""""1 OR 2"""""",TEST_CLAUSE,CASE_INSENSITIVE_TEST @Value(path_windows) CONTAINS \05 - Průvodní technická dokumentace (PTD)\
      CASE_INSENSITIVE_TEST @Value(path_windows) CONTAINS \PTD\",05 - Průvodní technická dokumentace (PTD),"BOOL_OP,OR,COMPOSITE_TEST,""""""1 OR 2"""""",TEST_CLAUSE,CASE_INSENSITIVE_TEST @Value(path_windows) CONTAINS \06 - Dokumentace skutečného stavu (As Built)\
      CASE_INSENSITIVE_TEST @Value(path_windows) CONTAINS \DSS\",06 - Dokumentace skutečného stavu (As Built)
    02 - Dokumenty managementu - Ostatn -> Junction
    03 - Projektová dokumentace (PD) -> Junction
    04 - Technická dokumentace (TD) -> Junction
    05 - Průvodní technická dokumentace (PTD) -> Junction
    06 - Dokumentace skutečného stavu (As Built) -> Junction
Junction
    -> FeatureMerger [REQUESTOR]

Bookmark: Kontrola souborů Seznam vs soubory ve složce
Note: Odebere chybové záznamy
FeatureMerger
    ATTR_ACCUM_MODE = Merge Supplier
    ATTR_CONFLICT_RES = Use Requestor
    IGNORE_NULLS = No
    JOIN_KEYS = @Value(path_windows) @Value(Cesta ke slozce Seznamu)@Value(Cesta elektronickeho souboru) AUTO
    MERGE_TYPE = Attributes Only
    PROCESS_DUPS = NO
    REJECT_NULL_MISSING_KEYS = No
    SUPPLIERS_FIRST = No
    UNMERGED_REQUESTOR -> FeatureMerger_2 [SUPPLIER]
FeatureMerger_2
    ATTR_ACCUM_MODE = Merge Supplier
    ATTR_CONFLICT_RES = Use Requestor
    IGNORE_NULLS = No
    JOIN_KEYS = @Value(Cesta ke slozce Seznamu)@Value(Cesta elektronickeho souboru) @Value(path_windows) AUTO
    MERGE_TYPE = Attributes Only
    PROCESS_DUPS = NO
    REJECT_NULL_MISSING_KEYS = No
    SUPPLIERS_FIRST = No
    MERGED -> Junction_9
    UNMERGED_REQUESTOR -> AttributeManager_5
    UNUSED_SUPPLIER -> AttributeManager_4
AttributeManager_5
    ATTR_TABLE:
      SET_TO Atribut = Cesta elektronického souboru
      SET_TO Hodnota atributu = -
      SET_TO Popis chyby = Nenalezen v adresari
      SET_TO FileName = @SubstringRegularExpression(@Value(Cesta elektronickeho souboru),(?:[^\\/](?!(\\|/)))+$,0,0,0,caseSensitive=TRUE)
      SET_TO Sheet_name = Chyby v Seznamu dokumentace
      RENAME_SET_VALUE xlsx_row_id > Cislo radku
      REMOVE Cesta k Seznamu
      REMOVE Cesta ke slozce Seznamu
      REMOVE Název Seznamu bez prip
      REMOVE Název Seznamu
      REMOVE fme_feature_type
      REMOVE Cislo SO
      REMOVE Oznaceni PS/DPS
      REMOVE Typ dokumentu
      REMOVE Podtyp dokumentu
      REMOVE DCC A1
      REMOVE Nazev dokumentu
      REMOVE Doplnujici nazev predmetu, umisteni
      REMOVE Projekcni oznaceni (KKS)
      REMOVE Archivni cislo dokumentu / Nazev souboru
      REMOVE Pocet listu v dokumentu
      REMOVE Revize dokumentu
      REMOVE Datum vytvoreni
      REMOVE Podslozka
      REMOVE Typ akce
      REMOVE Kod projektu
      REMOVE Popis akce
      REMOVE Elektrarna
      REMOVE Zhotovitel
      REMOVE Cislo JMA
      REMOVE Location
      REMOVE Faze
      REMOVE OJ
    USER_EXPOSED_ATTRIBUTES = Atribut
    -> Junction_13
AttributeManager_4
    ATTR_TABLE:
      SET_TO Cislo radku (varchar(200)) = NA
      SET_TO Atribut (varchar(200)) = NA
      SET_TO Hodnota atributu (varchar(200)) = NA
      SET_TO Popis chyby (varchar(200)) = Soubor není v Seznamu
      RENAME_SET_VALUE path_windows > Cesta elektronickeho souboru (varchar(200))
      SET_TO FileName (varchar(200)) = @SubstringRegularExpression(@Value(Cesta elektronickeho souboru),(?:[^\\/](?!(\\|/)))+$,0,0,0,caseSensitive=TRUE)
      SET_TO Sheet_name (varchar(200)) = Chyby v Seznamu dokumentace
      REMOVE path_directory_windows (varchar(200))
    -> Junction_13
Note: Sorter : Input
Junction_13
    -> Junction_14

Bookmark: Zpracování hlavičky
Junction_5
    -> Cislo_JMA
Cislo_JMA: StringSearcher
    CASE = no
    MATCHED_RESULT_ATTR = Cislo JMA
    REGEXP = [0-9]{4}
    STRING_TO_SEARCH = @Value(Kod projektu)
    MATCHED -> Location
Note: Nutné postupně rozšířit
Location: AttributeValueMapper
    DEFAULT_VALUE = Error_Location
    DIRECTION = Forward (Source To Destination)
    LUT = PPC,PPCEPC,ELE,ELE,EPR,EPR,ETU,ETU,EGT,EGT,TTR,TTR
    SRC = Elektrarna
    VAL_ATTR = Location
    -> Faze
Faze: AttributeValueMapper
    DEFAULT_VALUE = Error_Faze
    DIRECTION = Forward (Source To Destination)
    LUT = PZ,Fáze 03 - Podnikatelský záměr,ZP,Fáze 04 - Záměr projektu,PP,Fáze 05 - Příprava,RE,Fáze 06 - Realizace,JMA,Fáze 08 - JMA a rozvoj elektrárny,SKEN,Fáze 09 - Skenované dokumenty
    SRC = Typ akce
    VAL_ATTR = Faze
    -> OJ
Note: Nutné postupně rozšířit
OJ: AttributeValueMapper
    DEFAULT_VALUE = Error_OJ
    DIRECTION = Forward (Source To Destination)
    LUT = EGT,Energotrans,ELE,Elektrárna Ledvice,PPC,Elektrárna PPC Počerady,EPR,Elektrárna Prunéřov,TTR,Teplárna Trmice,ETU,Elektrárna Tušimice
    SRC = Elektrarna
    VAL_ATTR = OJ
    -> FeatureMerger_2 [REQUESTOR]
    -> Junction_4
Note: Sampler_2 : Input
Junction_4
    -> Junction_12

Bookmark: Přejmenování duplicitních souborů v Seznamu a ve složce
Junction_9
    -> AttributeManager_13
AttributeManager_13
    ATTR_TABLE:
      SET_TO FileName (varchar(200)) = @SubstringRegularExpression(@Value(Cesta elektronickeho souboru),(?:[^\\/](?!(\\|/)))+$,0,0,0,caseSensitive=TRUE)
      SET_TO FileNetPath_To_EDPPath (varchar(200)) = FME_CONDITIONAL:DEFAULT_VALUE'@SubstringRegularExpression(@Value(Cesta elektronickeho souboru),^[^\\]*,0,0,0,caseSensitive=TRUE)\@Value(FileName)'BOOL_OP;OR;COMPOSITE_TEST;1;TEST Podslozka ATTRIBUTE_HAS_A_VALUE _FME_BLANK_STRING_'@SubstringRegularExpression(@Value(Cesta elektronickeho souboru),^[^\\]*,0,0,0,caseSensitive=TRUE)\@Value(Podslozka)\@Value(FileName)'FME_NUM_CONDITIONS2___
    USER_EXPOSED_ATTRIBUTES = PathToFiles,Cislo radku,Podslozka FileNetPath
    -> DuplicateFilter_4
Note: Duplicitni windows_path po nahrani do DM a vysypani zpět do WIN
DuplicateFilter_4
    INPUT_ORDERED_CHOICE = No
    KEYATTR = FileNetPath_To_EDPPath
    UNIQUE -> FeatureMerger_4 [REQUESTOR]
    DUPLICATE -> FeatureMerger_4 [SUPPLIER]
FeatureMerger_4
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(FileNetPath_To_EDPPath) @Value(FileNetPath_To_EDPPath) AUTO
    MERGE_TYPE = Attributes Only
    PROCESS_DUPS = YES
    REJECT_NULL_MISSING_KEYS = No
    SUPPLIERS_FIRST = No
    MERGED -> Counter_2
    UNMERGED_REQUESTOR -> Junction_10
    UNMERGED_REQUESTOR -> AttributeManager_21
    USED_SUPPLIER -> Counter_2
AttributeManager_21
    ATTR_TABLE:
      RENAME_SET_VALUE Cesta elektronickeho souboru > N (varchar(200))
      REMOVE FileName (varchar(200))
      REMOVE FileNetPath_To_EDPPath (varchar(200))
      REMOVE Podslozka (varchar(200))
      REMOVE path_directory_windows (varchar(200))
      REMOVE Cesta ke slozce Seznamu (buffer)
      REMOVE Název Seznamu bez prip (buffer)
      REMOVE Cislo SO (varchar(200))
      REMOVE Oznaceni PS/DPS (varchar(200))
      REMOVE Typ dokumentu (varchar(200))
      REMOVE Podtyp dokumentu (varchar(200))
      REMOVE DCC A1 (varchar(200))
      REMOVE Nazev dokumentu (varchar(200))
      REMOVE Doplnujici nazev predmetu, umisteni (varchar(200))
      REMOVE Projekcni oznaceni (KKS) (varchar(200))
      REMOVE Archivni cislo dokumentu / Nazev souboru (varchar(200))
      REMOVE Pocet listu v dokumentu (varchar(200))
      REMOVE Revize dokumentu (varchar(200))
      REMOVE Datum vytvoreni (varchar(200))
      REMOVE Typ akce (varchar(200))
      REMOVE Kod projektu (varchar(200))
      REMOVE Popis akce (varchar(200))
      REMOVE Elektrarna (varchar(200))
      REMOVE Zhotovitel (varchar(200))
      REMOVE Cislo JMA (buffer)
      REMOVE Location (buffer)
      REMOVE Faze (buffer)
      REMOVE OJ (buffer)
      REMOVE path_windows (varchar(200))
    -> AttributeManager_20
Counter_2
    CNT_ATTR = Poradove cislo
    GROUP_BY = FileNetPath_To_EDPPath
    SCOPE = Local
    START = 1
    -> AttributeManager_9
Note: Tvorba nových názvů a cesty souborů
AttributeManager_9
    ATTR_TABLE:
      SET_TO Filename_bez_extenze = @Substring(@Value(FileName),0,@FindRegularExpression(@Value(FileName),(\.)(?!.*\.),0,0,0,caseSensitive=TRUE))
      SET_TO New_PathToFiles = @ReplaceString(@Value(Cesta elektronickeho souboru),@Value(Filename_bez_extenze),@Value(Filename_bez_extenze)_@Value(Poradove cislo),caseSensitive=TRUE)
      SET_TO New_Filename = @ReplaceString(@Value(FileName),@Value(Filename_bez_extenze),@Value(Filename_bez_extenze)_@Value(Poradove cislo),caseSensitive=TRUE)
    USER_EXPOSED_ATTRIBUTES = New_Filename,New_Cesta elektronickeho souboru,Filename_bez_extenze,Cesta elektronickeho souboru
    -> PythonCaller
Note: Změna názvu souborů ve složce / Úspěch - Succes = 1 / Neúspěch - Succes = 0
PythonCaller
    NEW_ATTRIBUTES = Succes
    PYTHONSOURCE:
      import fme
      import fmeobjects
      import os
      import sys


      def FileRenamer(feature):

              original_file_name = feature.getAttribute('FileName')
              new_file_name = feature.getAttribute('New_Filename')
              orig_file_path = feature.getAttribute('path_directory_windows')
              new_file_path = 'dfs03.cezdata.corp\CEZ\DKE\9050060_ŘTKE\TPKE\RIZEK\JMA do DOCMAN\Testovací dávky ICC\ETU_0806_JMA\Python_test'
              try:
                  os.rename(os.path.join(orig_file_path, original_file_name), os.path.join(orig_file_path, new_file_name))
                  feature.setAttribute("Succes", 1)
              except Exception as e:
                  error = 'Error on line ' + str(sys.exc_info()[-1].tb_lineno) + ' - ' + str(type(e).__name__) + ' - ' + str(e)
                  print(error)
                  feature.setAttribute("_error", error)
                  feature.setAttribute("Succes", 0)
    PYTHONSYMBOL = FileRenamer
    -> AttributeManager_11
    -> AttributeManager_10
    -> Popis_upozorneni
Note: Změna názvů souborů v Att "Elektronická cesta souboru" v FME
AttributeManager_10
    ATTR_TABLE:
      SET_TO FileName = @Value(New_Filename)
      SET_TO Cesta elektronickeho souboru = @Value(New_PathToFiles)
      REMOVE Succes
      REMOVE New_Filename
      REMOVE New_PathToFiles
      REMOVE Filename_bez_extenze
    USER_EXPOSED_ATTRIBUTES = N,PathToFiles
    -> Junction_10
Junction_10
    -> Podtyp_na_DCCA2A3
Popis_upozorneni: AttributeManager
    ATTR_TABLE:
      RENAME_SET_VALUE xlsx_row_id > Cislo radku
      SET_TO Atribut = Název souboru
      SET_TO Hodnota atributu = "@Value(FileName)" -> "@Value(New_Filename)"
      SET_TO Popis chyby = Soubor byl přejmenován z důvodu konfliktu při zkracování složek. Došlo také k úpravě Seznamu
      SET_TO Cesta elektronickeho souboru = "@Value(Cesta elektronickeho souboru)" -> "@Value(New_PathToFiles)"
      SET_TO FileName = @Value(New_Filename)
      SET_TO Sheet_name = Upozornění na změny v Seznamu
      SET_TO Zmena v Excelu = Ne
      REMOVE FileNetPath_To_EDPPath
      REMOVE numReferences
      REMOVE Filename_bez_extenze
      REMOVE New_PathToFiles
      REMOVE New_Filename
      REMOVE Poradove cislo
      REMOVE Cesta k Seznamu
      REMOVE Název Seznamu
      REMOVE Podslozka
      REMOVE fme_feature_type
      REMOVE path_directory_windows
      REMOVE Cesta ke slozce Seznamu
      REMOVE Název Seznamu bez prip
      REMOVE Cislo SO
      REMOVE Oznaceni PS/DPS
      REMOVE Typ dokumentu
      REMOVE Podtyp dokumentu
      REMOVE DCC A1
      REMOVE Nazev dokumentu
      REMOVE Doplnujici nazev predmetu, umisteni
      REMOVE Projekcni oznaceni (KKS)
      REMOVE Archivni cislo dokumentu / Nazev souboru
      REMOVE Pocet listu v dokumentu
      REMOVE Revize dokumentu
      REMOVE Datum vytvoreni
      REMOVE Typ akce
      REMOVE Kod projektu
      REMOVE Popis akce
      REMOVE Elektrarna
      REMOVE Zhotovitel
      REMOVE Cislo JMA
      REMOVE Location
      REMOVE Faze
      REMOVE OJ
      REMOVE path_windows
      REMOVE Succes
    -> FeatureMerger_9 [REQUESTOR]
Note: Pokud se Python nebo zápis do Excelu sekne, nemělo by projít dál
AttributeManager_11
    ATTR_TABLE:
      SET_TO N = @Value(New_PathToFiles)
      REMOVE New_PathToFiles
      REMOVE FileName
      REMOVE New_Filename
      REMOVE Filename_bez_extenze
      REMOVE FileNetPath_To_EDPPath
      REMOVE Poradove cislo
      REMOVE numReferences
      REMOVE Podslozka
      REMOVE path_directory_windows
      REMOVE Cesta ke slozce Seznamu
      REMOVE Název Seznamu bez prip
      REMOVE Cislo SO
      REMOVE Oznaceni PS/DPS
      REMOVE Typ dokumentu
      REMOVE Podtyp dokumentu
      REMOVE DCC A1
      REMOVE Nazev dokumentu
      REMOVE Doplnujici nazev predmetu, umisteni
      REMOVE Projekcni oznaceni (KKS)
      REMOVE Archivni cislo dokumentu / Nazev souboru
      REMOVE Pocet listu v dokumentu
      REMOVE Revize dokumentu
      REMOVE Datum vytvoreni
      REMOVE Typ akce
      REMOVE Kod projektu
      REMOVE Popis akce
      REMOVE Elektrarna
      REMOVE Zhotovitel
      REMOVE Cislo JMA
      REMOVE Location
      REMOVE Faze
      REMOVE OJ
      REMOVE path_windows
      REMOVE Succes
      REMOVE Cesta elektronickeho souboru
    USER_EXPOSED_ATTRIBUTES = N
    -> AttributeManager_20
TestFilter_6
    DEFAULT_VALUE = <UNFILTERED>
    PASSED_TEST_GROUP_OUTPUT = FIRST
    TEST_LIST = "BOOL_OP,OR,COMPOSITE_TEST,""""""1"""""",TEST_CLAUSE,CASE_INSENSITIVE_TEST @Value(fme_feature_type_name) BEGINS_WITH SEZNAM",@Value(fme_feature_type_name) BEGINS_WITH SEZNAM
    @Value(fme_feature_type_name) BEGINS_WITH SEZNAM -> AttributeManager_20
AttributeManager_20
    ATTR_TABLE:
      SET_TO Pevna_cesta (varchar(200)) = $(Pevna_cesta)
      SET_TO Slozka (varchar(200)) = $(Slozka)
    -> FeatureWriter_3 [Output]
Note: Změna názvu souborů v Att "Elektronická cesta souboru" v Seznamu
FeatureWriter_3
    DATASET = @Value(Pevna_cesta)\@Value(Slozka)\@Value(Název Seznamu)
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = Yes
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TEMPLATEFILE = @Value(Cesta k Seznamu)
    XLSXW_TRUNCATE_TABLE = No
    XLSXW_WRITER_MODE = Update
    SUMMARY -> Popis_upozorneni_2
Popis_upozorneni_2: AttributeManager
    ATTR_TABLE:
      SET_TO Zmena v Excelu = Ano
      REMOVE _feature_types{}.count
      REMOVE _feature_types{}.name
      REMOVE _dataset
      REMOVE _total_features_written
    -> FeatureMerger_9 [SUPPLIER]
FeatureMerger_9
    ATTR_ACCUM_MODE = Merge Supplier
    ATTR_CONFLICT_RES = Use Supplier
    IGNORE_NULLS = No
    JOIN_KEYS = 1 1 AUTO
    MERGE_TYPE = Attributes Only
    PROCESS_DUPS = NO
    REJECT_NULL_MISSING_KEYS = No
    SUPPLIERS_FIRST = No
    MERGED -> Tester_4
    UNMERGED_REQUESTOR -> Tester_4
Tester_4
    BOOL_OP = OR
    TEST_CLAUSE = TEST @Value(Zmena v Excelu) = Ano
    TEST_MODE = TEST
    FAILED -> AttributeManager_12
Note: Zakončit
AttributeManager_12
    ATTR_TABLE:
      SET_TO Popis chyby = Chyba  zapisu PathToFiles do Excelu
      SET_TO Sheet_name = @Value(Zmena v Excelu)

Bookmark: Úprava a transformace dat
Podtyp_na_DCCA2A3: AttributeValueMapper
    DEFAULT_VALUE = @Value(Podtyp dokumentu)
    LUT = AZ,QA,BSCH,FA,BST,QB,DL,BC,DLI,DA,DOL,CD,DPP,DC,DPU,DC,DS,BA,DZ,WT,DÚ,WT,EO,FF,ES,AB,FA,CE,FG,FF,FO,CC,FP,FE,FSCH,FF,FSV,FS,HM,BE,IEC,EB,ISO,EB,KA,DE,KCV,TA,KS,MB,KV,FT,LI,CB,MIN,DC,MO,QC,MS,FA,MSB,LH,MSS,LD,MSV,LD,NA,CA,NKI,DC,NKO,DC,NKU,DC,NN,WA,NSS,EA,NSV,EA,NV,TA,OB,AA,OC,QC,OJ,CD,OP,CH,OPR,CB,OS,FS,OZ,BH,OŠ,CF,PA,QA,PD,CA,PDH,WT,PID,FB,PJ,CF,PK,QA,PL,BC,PM,DC,PN,BH,POD,AC,POS,QA,POZ,QC,PP,BB,PPO,BS,PPT,CA,PPV,FT,PRI,QB,PRK,QA,PRO,DE,PRS,MA,PS,FB,PSO,DB,PSYS,DB,PZ,MB,PZA,QA,PŠ,BT,RI,BE,RN,BS,RV,TB,SCHP,FT,SCHZ,MA,SD,BA,SDI,FF,SDOC,AB,SF,PF,SKV,QA,SL,FF,SM,EC,SMA,PA,SMB,EC,SML,CC,SMO,EC,SNA,FQ,SND,PB,SO,FB,SP,EC,SPD,BD,SPL,PC,SPO,MB,SPS,BG,SPV,MB,SPZ,EC,SS,EA,SSE,EC,SSI,FP,ST,PD,STR,DB,SU,PL,SVR,PD,SVS,LD,SVY,TL,SZ,EC,SČ,PB,SŠ,PB,SŽ,CB,TL,AA,TP,DF,TS,FB,TSP,EC,TZ,DD,V3D,TB,VA,DD,VB,LH,VI,DC,VKB,LH,VKS,LD,VL,ED,VP,TC,VPO,TC,VR,TB,VRH,TB,VS,LU,VSK,LC,VUB,LH,VUS,LD,VUZ,LU,VV,TC,VVK,LB,VVT,LC,VZA,LB,VZB,LH,VZD,FC,VZS,LD,ZA,QA,ZI,BS,ZK,QA,ZL,CG,ZOI,BB,ZOJ,BB,ZON,QA,ZOO,QA,ZOP,QC,ZPR,BB,ZS,MA,ZSCH,MA,ZT,MA,Zkratka,A2A3,ÚAP,LA,ÚL,AA,ÚPL,BS,ČS,FF
    MAPPING_DIRECTION = FORWARD
    SRC = Podtyp dokumentu
    VAL_ATTR = SegmentationaccordingtoCSNEN6135A3
    -> Typ_dokumentu_transformace_DM
Typ_dokumentu_transformace_DM: AttributeValueMapper
    DEFAULT_VALUE = @Value(Typ dokumentu)
    LUT = DSS,TDTT,OST,TDMR,PD,TDTD,PTD,TDPC,TD,TDOP
    MAPPING_DIRECTION = FORWARD
    SRC = Typ dokumentu
    VAL_ATTR = DocumentType
    -> PS_DPS
PS_DPS: AttributeCreator
    ATTR_TABLE:
      SET_TO PS (varchar(200)) = @Left(@Value(Oznaceni PS/DPS),2)
      SET_TO DPS (varchar(200)) = @Right(@Value(Oznaceni PS/DPS),2)
    -> AttributeCreator_5
AttributeManager
    ATTR_TABLE:
      SET_TO AuthorDM (varchar(200)) = $(KPJM)
      RENAME_SET_VALUE Elektrarna > Code (varchar(200))
      RENAME_SET_VALUE Zhotovitel > CompanyIssuing (varchar(200))
      RENAME_SET_VALUE Datum vytvoreni > Date (varchar(200))
      RENAME_SET_VALUE Nazev dokumentu > DocumentDescription (varchar(200))
      SET_TO DocumentState (varchar(200)) = 20
      RENAME_SET_VALUE Doplnujici nazev predmetu, umisteni > DocumentSubject (varchar(200))
      SET_TO DocumentSubType (varchar(200)) = AAK
      SET_TO DocumentTitle (varchar(200)) = @Value(DocumentDescription) / @Value(DocumentSubject) // @Value(Archivni cislo dokumentu / Nazev souboru)
      RENAME_SET_VALUE Projekcni oznaceni (KKS) > EquipmentID (varchar(200))
      SET_TO Id (varchar(200))
      SET_TO ImportedDocument (varchar(200)) = true
      SET_TO Maker (varchar(200)) = @Value(CompanyIssuing)
      SET_TO OriginalDocumentVersionSeriesId (varchar(200))
      SET_TO PackNumber (varchar(200)) = @Value(Typ akce)/@Value(Kod projektu)
      SET_TO Phase (varchar(200))
      SET_TO ProjectId (buffer) = @Value(Location)
      RENAME_SET_VALUE Revize dokumentu > Revision (varchar(200))
      RENAME_SET_VALUE DCC A1 > SegmentationaccordingtoCSNEN6135A1 (varchar(200))
      RENAME_SET_VALUE Pocet listu v dokumentu > Sheet (varchar(200))
      SET_TO SO (varchar(200)) = FME_CONDITIONAL:DEFAULT_VALUE'@Value(Cislo SO)'BOOL_OP;OR;COMPOSITE_TEST;1;TEST @Value(Cislo SO) = NA''FME_NUM_CONDITIONS2___
      RENAME_SET_VALUE Archivni cislo dokumentu / Nazev souboru > SupplierArchivalNo (varchar(200))
      SET_TO TradePackage (varchar(200)) = @Value(Typ akce)@Value(Cislo JMA)
      SET_TO FileName (varchar(200)) = @SubstringRegularExpression(@Value(Cesta elektronickeho souboru),(?:[^\\/](?!(\\|/)))+$,0,0,0,caseSensitive=TRUE)
      SET_TO předpříprava (varchar(200)) = \@Value(OJ)\@Value(Faze)\@Value(Cislo JMA) @Value(Popis akce)\@SubstringRegularExpression(@Value(Cesta elektronickeho souboru pro DM),^[^\\]*,0,0,0,caseSensitive=TRUE)
      SET_TO FileNetPath (varchar(200)) = FME_CONDITIONAL:DEFAULT_VALUE'@Value(předpříprava)'BOOL_OP;OR;COMPOSITE_TEST;1;TEST Podslozka ATTRIBUTE_HAS_A_VALUE _FME_BLANK_STRING_'@Value(předpříprava)\@Value(Podslozka)'FME_NUM_CONDITIONS2___
      RENAME_SET_VALUE Cesta elektronickeho souboru > PathToFiles (varchar(200))
      REMOVE fme_feature_type (varchar(200))
      REMOVE OJ (buffer)
      REMOVE path_windows (varchar(200))
      REMOVE Cesta ke slozce Seznamu (buffer)
      REMOVE Název Seznamu bez prip (buffer)
      REMOVE Poradove cislo (int64)
      REMOVE Cislo SO (varchar(200))
      REMOVE path_directory_windows (varchar(200))
      REMOVE Cesta elektronickeho souboru pro DM (varchar(200))
      REMOVE Docman_File_4th_level (buffer)
      REMOVE numReferences (uint32)
      REMOVE Podslozka (varchar(200))
      REMOVE Oznaceni PS/DPS (varchar(200))
      REMOVE Typ akce (varchar(200))
      REMOVE Kod projektu (varchar(200))
      REMOVE Popis akce (varchar(200))
      REMOVE Cislo JMA (buffer)
      REMOVE Faze (buffer)
    USER_EXPOSED_ATTRIBUTES = PathToFiles,Order,Oznaceni_PS_DPS,Doplnujici_nazev_predmetu_umisteni,Stav_dokumentu,Datum_vytvoreni,Typ_dokumentu_DMDI
    -> Nahrada_carky_za_tildu

Bookmark: Úprava cesty elektronického souboru na delší názvy složek lvl 4
AttributeCreator_5
    ATTR_TABLE = SET_TO Cesta elektronickeho souboru pro DM (varchar(200)) = @Value(Cesta elektronickeho souboru)
    -> AttributeValueMapper_2
AttributeValueMapper_2
    LUT = OST,02 - Dokumenty managementu - Ostatní,PD,03 - Projektová dokumentace (PD),TD,04 - Technická dokumentace (TD),PTD,05 - Průvodní technická dokumentace (PTD),DSS,06 - Dokumentace skutečného stavu (As Built)
    MAPPING_DIRECTION = FORWARD
    SRC = Typ dokumentu
    VAL_ATTR = Docman_File_4th_level
    -> StringReplacer_2
StringReplacer_2
    CASE = NO
    FIND_TEXT = @Value(Typ dokumentu)\
    NO_MATCH = _FME_NO_OP_
    REGEXP = NO
    REPLACE_TEXT = @Value(Docman_File_4th_level)\
    SRC_ATTRS = Cesta elektronickeho souboru pro DM
    -> AttributeManager

Bookmark: Dodatečná úprava EquipmentID
Nahrada_carky_za_tildu: StringReplacer
    CASE = NO
    FIND_TEXT = ,
    NO_MATCH = _FME_NO_OP_
    REGEXP = NO
    REPLACE_TEXT = ~
    SRC_ATTRS = EquipmentID
    -> Nahrada_mezery_za_nic
Nahrada_mezery_za_nic: StringReplacer
    CASE = NO
    FIND_TEXT = " "
    NO_MATCH = _FME_NO_OP_
    REGEXP = NO
    SRC_ATTRS = EquipmentID
    -> Nahrada_podtrzitka_za_nic
Nahrada_podtrzitka_za_nic: StringReplacer
    CASE = NO
    FIND_TEXT = _
    NO_MATCH = _FME_NO_OP_
    REGEXP = NO
    SRC_ATTRS = EquipmentID
    -> DateTimeConverter

Bookmark: Dodatečná úprava Date
DateTimeConverter
    DATETIME_ATTR = Date
    OUT_FORMAT = %Y-%m-%d
    PASSTHROUGH = NO
    REPAIR_INPUT = YES
    TEST_INPUT = 20200915181608
    -> EquipmentID_checker

Bookmark: Kontrola na délku cest
EquipmentID_checker
    EQUIPMENTID = @Value(EquipmentID)
    ROWID = @Value(xlsx_row_id)
    Delka_ok -> Test_delky_zaslozkovani_2
    Delka_err -> Popis_chyby_SubType_5
    Delka_err -> Test_delky_zaslozkovani_2
Junction_15
    -> AttributeCreator_3
Popis_chyby_SubType_5: AttributeCreator
    ATTR_TABLE:
      SET_TO Atribut = Projekční označení (KKS)

      SET_TO Hodnota atributu = @Value(EquipmentID)
      SET_TO Popis chyby = Hodnota některého prvku je příliš dlouhá
      SET_TO Cesta elektronickeho souboru = @Value(PathToFiles)
      SET_TO Sheet_name = Chyby v Seznamu dokumentace
    -> Junction_17
Note: DuplicateFilter : Input
Junction_17
    -> Junction_18

Bookmark: New Bookmark
Note: Kontrola na délku cesty FileNetPath_To_EDPPath < 240 zn; Sheet < 9 zn
Test_delky_zaslozkovani_2: TestFilter
    DEFAULT_VALUE = <UNFILTERED>
    PASSED_TEST_GROUP_OUTPUT = FIRST
    TEST_LIST = "BOOL_OP,OR,COMPOSITE_TEST,""""""1"""""",TEST_CLAUSE,TEST @Evaluate(@StringLength(@Value(FileNetPath_To_EDPPath))) <= 200",Delka FileNetPath_To_EDPPath <=200
    Delka FileNetPath_To_EDPPath <=200 -> Test_delky_zaslozkovani_3
    <UNFILTERED> -> Popis_chyby_SubType_3
    <UNFILTERED> -> Test_delky_zaslozkovani_3
Note: Na tohle ještě kouknout
Popis_chyby_SubType_3: AttributeCreator
    ATTR_TABLE:
      SET_TO Atribut = FileNetPath_To_EDPPath
      SET_TO Hodnota atributu = @Value(FileNetPath_To_EDPPath)
      SET_TO Popis chyby = Hodnota cesty je příliš dlouhá
      SET_TO Cesta elektronickeho souboru = @Value(PathToFiles)
      SET_TO Sheet_name = Chyby v Seznamu dokumentace
    -> Junction_17

Bookmark: New Bookmark
Note: Kontrola na délku cesty FileNetPath_To_EDPPath < 240 zn; Sheet < 9 zn
Test_delky_zaslozkovani_3: TestFilter
    DEFAULT_VALUE = >255
    PASSED_TEST_GROUP_OUTPUT = FIRST
    TEST_LIST = "BOOL_OP,OR,COMPOSITE_TEST,""""""1"""""",TEST_CLAUSE,TEST @Evaluate(@StringLength(\\?\unc\cezdata.corp\sdp\cez\dke\9050060_řtke\tpke\rizek\ICC Prod\ELNA\$(Slozka)\@Value(PathToFiles))) <= 255",<=255
    <=255 -> Junction_15
    >255 -> Popis_chyby_SubType_4
    >255 -> Junction_15
Popis_chyby_SubType_4: AttributeCreator
    ATTR_TABLE:
      SET_TO Atribut = Délka cesty
      SET_TO Hodnota atributu = \\?\unc\cezdata.corp\sdp\cez\dke\9050060_řtke\tpke\rizek\ICC Prod\ELNA\$(Slozka)\@Value(PathToFiles)
      SET_TO Popis chyby = Hodnota cesty je příliš dlouhá (@StringLength(\\?\unc\cezdata.corp\sdp\cez\dke\9050060_řtke\tpke\rizek\ICC Prod\ELNA\$(Slozka)\@Value(PathToFiles)))
      SET_TO Cesta elektronickeho souboru = @Value(PathToFiles)
      SET_TO Sheet_name = Chyby v Seznamu dokumentace
    -> Junction_17

Bookmark: Multicontent
AttributeCreator_3
    ATTR_TABLE = SET_TO Extenze = @Substring(@Value(FileName),@add(@FindRegularExpression(@Value(FileName),(\.)(?!.*\.),0,0,0,caseSensitive=TRUE),1))
    -> AttributeValueMapper
AttributeValueMapper
    DEFAULT_VALUE = 5
    LUT = PDF,1,pdf,1,DOCX,2,docx,2,DOC,2,doc,2
    MAPPING_DIRECTION = FORWARD
    SRC = Extenze
    VAL_ATTR = Priorita extenze
    -> Sorter_2
Sorter_2
    SORT_PARM = Priorita extenze NUMERIC ASCENDING
    SORTED -> DuplicateFilter_2
DuplicateFilter_2
    INPUT_ORDERED_CHOICE = No
    KEYATTR = SupplierArchivalNo FileNetPath
    UNIQUE -> FeatureMerger_6 [REQUESTOR]
    DUPLICATE -> FeatureMerger_6 [SUPPLIER]
FeatureMerger_6
    ATTR_ACCUM_MODE = Merge Supplier
    ATTR_CONFLICT_RES = Use Requestor
    IGNORE_NULLS = No
    JOIN_KEYS = @Value(SupplierArchivalNo) @Value(SupplierArchivalNo) AUTO @Value(FileNetPath) @Value(FileNetPath) AUTO
    LIST_ATTRS_TO_INCLUDE = FileName PathToFiles
    LIST_NAME = Multicontent
    MERGE_TYPE = Attributes Only
    PROCESS_DUPS = NO
    REJECT_NULL_MISSING_KEYS = No
    SUPPLIERS_FIRST = No
    MERGED -> ListConcatenator
    UNMERGED_REQUESTOR -> Junction_11
ListConcatenator
    DROP_EMPTY_PARTS = Yes
    LIST_ATTR = Multicontent{}.FileName
    SEP = ~
    VAL_ATTR = FileName_Multi
    -> ListConcatenator_2
ListConcatenator_2
    DROP_EMPTY_PARTS = Yes
    LIST_ATTR = Multicontent{}.PathToFiles
    SEP = ~
    VAL_ATTR = PathToFiles_Multi
    -> AttributeManager_8
AttributeManager_8
    ATTR_TABLE:
      SET_TO FileName = @Value(FileName)~@Value(FileName_Multi)
      SET_TO PathToFiles = @Value(PathToFiles)~@Value(PathToFiles_Multi)
    USER_EXPOSED_ATTRIBUTES = FileNetPath,Filename_raw,Dup_FileNetPath,Dup_Filename_raw,path_directory_windows,Dup_path_directory_windows
    -> Junction_11
Junction_11
    -> Test_ciselniku_DCC_A2A3_2 [REQUESTOR]

Bookmark: New Bookmark
Test_ciselniku_DCC_A2A3_2: FeatureMerger
    ATTR_ACCUM_MODE = Merge Supplier
    ATTR_CONFLICT_RES = Use Requestor
    IGNORE_NULLS = No
    JOIN_KEYS = @Value(SegmentationaccordingtoCSNEN6135A3) @Value(value) AUTO
    MERGE_TYPE = Attributes Only
    PROCESS_DUPS = NO
    REJECT_NULL_MISSING_KEYS = Yes
    SUPPLIERS_FIRST = No
    MERGED -> Test_ciselniku_DCC_A1 [REQUESTOR]
    UNMERGED_REQUESTOR -> Popis_chyby_DCC_A2_A3_2
    UNMERGED_REQUESTOR -> Test_ciselniku_DCC_A1 [REQUESTOR]
    <REJECTED> -> Popis_chyby_DCC_A2_A3_2
    <REJECTED> -> Test_ciselniku_DCC_A1 [REQUESTOR]
Note: Rozlišuje missing a mimo číselník
Popis_chyby_DCC_A2_A3_2: AttributeCreator
    ATTR_TABLE:
      SET_TO Atribut = Podtyp dokumentu
      SET_TO Hodnota atributu = FME_CONDITIONAL:DEFAULT_VALUE'Nezadáno'BOOL_OP;OR;COMPOSITE_TEST;1;TEST SegmentationaccordingtoCSNEN6135A3 ATTRIBUTE_HAS_A_VALUE _FME_BLANK_STRING_'@Value(Podtyp dokumentu)'FME_NUM_CONDITIONS2___
      SET_TO Popis chyby = FME_CONDITIONAL:DEFAULT_VALUE'Hodnota nezadána'BOOL_OP;OR;COMPOSITE_TEST;1;TEST SegmentationaccordingtoCSNEN6135A3 ATTRIBUTE_HAS_A_VALUE _FME_BLANK_STRING_'Hodnota není v číselníku'FME_NUM_CONDITIONS2___
      SET_TO Cesta elektronickeho souboru = @Value(PathToFiles)
      SET_TO Sheet_name = Chyby v Seznamu dokumentace
    -> DuplicateFilter

Bookmark: New Bookmark
Test_ciselniku_DCC_A1: FeatureMerger
    ATTR_ACCUM_MODE = Merge Supplier
    ATTR_CONFLICT_RES = Use Requestor
    IGNORE_NULLS = No
    JOIN_KEYS = @Value(SegmentationaccordingtoCSNEN6135A1) @Value(value) AUTO
    MERGE_TYPE = Attributes Only
    PROCESS_DUPS = NO
    REJECT_NULL_MISSING_KEYS = Yes
    SUPPLIERS_FIRST = No
    MERGED -> Test_ciselniku_Doc_Type [REQUESTOR]
    UNMERGED_REQUESTOR -> Popis_chyby_DCC_A1_2
    UNMERGED_REQUESTOR -> Test_ciselniku_Doc_Type [REQUESTOR]
    <REJECTED> -> Popis_chyby_DCC_A1_2
    <REJECTED> -> Test_ciselniku_Doc_Type [REQUESTOR]
Note: Rozlišuje missing a mimo číselník
Popis_chyby_DCC_A1_2: AttributeCreator
    ATTR_TABLE:
      SET_TO Atribut = DCC A1
      SET_TO Hodnota atributu = FME_CONDITIONAL:DEFAULT_VALUE'Nezadáno'BOOL_OP;OR;COMPOSITE_TEST;1;TEST SegmentationaccordingtoCSNEN6135A1 ATTRIBUTE_HAS_A_VALUE _FME_BLANK_STRING_'@Value(SegmentationaccordingtoCSNEN6135A1)'FME_NUM_CONDITIONS2___
      SET_TO Popis chyby = FME_CONDITIONAL:DEFAULT_VALUE'Hodnota nezadána'BOOL_OP;OR;COMPOSITE_TEST;1;TEST SegmentationaccordingtoCSNEN6135A1 ATTRIBUTE_HAS_A_VALUE _FME_BLANK_STRING_'Hodnota není v číselníku'FME_NUM_CONDITIONS2___
      SET_TO Cesta elektronickeho souboru = @Value(PathToFiles)
      SET_TO Sheet_name = Chyby v Seznamu dokumentace
    -> DuplicateFilter

Bookmark: New Bookmark
Test_ciselniku_Doc_Type: FeatureMerger
    ATTR_ACCUM_MODE = Merge Supplier
    ATTR_CONFLICT_RES = Use Requestor
    IGNORE_NULLS = No
    JOIN_KEYS = @Value(DocumentType) @Value(value) AUTO
    MERGE_TYPE = Attributes Only
    PROCESS_DUPS = NO
    REJECT_NULL_MISSING_KEYS = Yes
    SUPPLIERS_FIRST = No
    MERGED -> Test_ciselniku_Doc_SubType [REQUESTOR]
    UNMERGED_REQUESTOR -> Popis_chyby_Typ_dokumentu_2
    UNMERGED_REQUESTOR -> Test_ciselniku_Doc_SubType [REQUESTOR]
    <REJECTED> -> Popis_chyby_Typ_dokumentu_2
    <REJECTED> -> Test_ciselniku_Doc_SubType [REQUESTOR]
Note: Rozlišuje missing a mimo číselník
Popis_chyby_Typ_dokumentu_2: AttributeCreator
    ATTR_TABLE:
      SET_TO Atribut = Typ dokumentu
      SET_TO Hodnota atributu = FME_CONDITIONAL:DEFAULT_VALUE'Nezadáno'BOOL_OP;OR;COMPOSITE_TEST;1;TEST Typ dokumentu ATTRIBUTE_HAS_A_VALUE _FME_BLANK_STRING_'@Value(Typ dokumentu)'FME_NUM_CONDITIONS2___
      SET_TO Popis chyby = FME_CONDITIONAL:DEFAULT_VALUE'Hodnota nezadána'BOOL_OP;OR;COMPOSITE_TEST;1;TEST Typ dokumentu ATTRIBUTE_HAS_A_VALUE _FME_BLANK_STRING_'Hodnota není v číselníku'FME_NUM_CONDITIONS2___
      SET_TO Cesta elektronickeho souboru = @Value(PathToFiles)
      SET_TO Sheet_name = Chyby v Seznamu dokumentace
    -> DuplicateFilter

Bookmark: New Bookmark
Test_ciselniku_Doc_SubType: FeatureMerger
    ATTR_ACCUM_MODE = Merge Supplier
    ATTR_CONFLICT_RES = Use Requestor
    IGNORE_NULLS = No
    JOIN_KEYS = @Value(DocumentSubType) @Value(value) AUTO
    MERGE_TYPE = Attributes Only
    PROCESS_DUPS = NO
    REJECT_NULL_MISSING_KEYS = No
    SUPPLIERS_FIRST = No
    MERGED -> Junction_6
    UNMERGED_REQUESTOR -> Popis_chyby_SubType_2
    UNMERGED_REQUESTOR -> Junction_6
    <REJECTED> -> Popis_chyby_SubType_2
    <REJECTED> -> Junction_6
Popis_chyby_SubType_2: AttributeCreator
    ATTR_TABLE:
      SET_TO Atribut = DocumentSubType
      SET_TO Hodnota atributu = @Value(DocumentSubType)
      SET_TO Popis chyby = Hodnota neni v číselníku
      SET_TO Cesta elektronickeho souboru = @Value(PathToFiles)
      SET_TO Sheet_name = Chyby v Seznamu dokumentace
    -> DuplicateFilter

Bookmark: Kontrola dle číselníků nebo pravidel
Junction_6
    -> FeatureMerger_3 [REQUESTOR]
Note: Junction_16 : Output
Junction_18
    -> DuplicateFilter
DuplicateFilter
    INPUT_ORDERED_CHOICE = No
    KEYATTR = xlsx_row_id
    UNIQUE -> FeatureMerger_3 [SUPPLIER]
    UNIQUE -> AttributeKeeper_2
    DUPLICATE -> AttributeKeeper_2
Note: Odebere chybové záznamy
FeatureMerger_3
    ATTR_ACCUM_MODE = Merge Supplier
    ATTR_CONFLICT_RES = Use Requestor
    IGNORE_NULLS = No
    JOIN_KEYS = @Value(xlsx_row_id) @Value(xlsx_row_id) AUTO
    MERGE_TYPE = Attributes Only
    PROCESS_DUPS = NO
    REJECT_NULL_MISSING_KEYS = No
    SUPPLIERS_FIRST = No
    UNMERGED_REQUESTOR -> StringReplacer
Note: Všechny chybové záznamy
AttributeKeeper_2
    CREATE_BULK_MODE_FEATURES = NO
    KEEP_ATTRS = Atribut,FileName,Hodnota atributu,Popis chyby,Cesta elektronickeho souboru,FileNetPath_To_EDPPath,Sheet_name,xlsx_row_id
    -> Sorter

Bookmark: Tvorba řádku pro Seznam
Note: OJ : Output
Junction_12
    -> Sampler_2
Sampler_2
    RATE = 1
    SAMPLE_MODE = No
    SAMPLE_TYPE_LONG = First N Features
    SAMPLED -> AttributeManager_3
AttributeManager_3
    ATTR_TABLE:
      SET_TO AuthorDM = $(KPJM)
      RENAME_SET_VALUE Elektrarna > Code
      RENAME_SET_VALUE Zhotovitel > CompanyIssuing
      SET_TO Date = @DateTimeFormat(@DateTimeNow(),%Y-%m-%d)
      SET_TO DocumentState = 20
      SET_TO DocumentSubType = AAK
      RENAME_SET_VALUE Název Seznamu bez prip > DocumentTitle
      SET_TO DocumentType = TDMM
      SET_TO ImportedDocument = true
      SET_TO ProjectId = @Value(Location)
      SET_TO SegmentationaccordingtoCSNEN6135A1 = B
      SET_TO SegmentationaccordingtoCSNEN6135A3 = AB
      RENAME_SET_VALUE Název Seznamu > FileName
      SET_TO FileNetPath = \@Value(OJ)\@Value(Faze)\@Value(Cislo JMA) @Value(Popis akce)
      SET_TO PathToFiles = @Value(FileName)
      REMOVE OJ
      REMOVE Cesta k Seznamu
      REMOVE Cesta ke slozce Seznamu
      REMOVE fme_feature_type
      REMOVE xlsx_row_id
      REMOVE Typ akce
      REMOVE Kod projektu
      REMOVE Popis akce
      REMOVE Cislo SO
      REMOVE Oznaceni PS/DPS
      REMOVE Typ dokumentu
      REMOVE Podtyp dokumentu
      REMOVE DCC A1
      REMOVE Nazev dokumentu
      REMOVE Doplnujici nazev predmetu, umisteni
      REMOVE Projekcni oznaceni (KKS)
      REMOVE Archivni cislo dokumentu / Nazev souboru
      REMOVE Pocet listu v dokumentu
      REMOVE Revize dokumentu
      REMOVE Cesta elektronickeho souboru
      REMOVE Datum vytvoreni
      REMOVE Podslozka
      REMOVE Cislo JMA
      REMOVE Location
      REMOVE Faze
    USER_EXPOSED_ATTRIBUTES = PathToFiles,Order,Oznaceni_PS_DPS,Doplnujici_nazev_predmetu_umisteni,Stav_dokumentu,Datum_vytvoreni,Typ_dokumentu_DMDI
    -> StringReplacer

Bookmark: Writers
AttributeManager_19
    ATTR_TABLE:
      SET_TO A (varchar(200)) = $(Pevna_cesta)
      SET_TO B (varchar(200)) = $(Slozka)
    -> FeatureWriter [Output]
Note: "@SubstringRegularExpression(@Value(Cesta k Seznamu),^(.*[\\\/]),0,0,0,caseSensitive=TRUE)"
FeatureWriter
    CSV2_COORDINATE_SYSTEM_GRANULARITY = FEATURE_TYPE
    CSV2_DELIMITER = ;
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = @Value(A)\@Value(B)
    DATASET_ATTR = _dataset
    FEATURE_TYPE_LIST_ATTR = _feature_types
    FORMAT = CSV2
    TOTAL_FEATURES_WRITTEN_ATTR = _total_features_written
AttributeManager_18
    ATTR_TABLE:
      SET_TO A (varchar(200)) = $(Pevna_cesta)
      SET_TO B (varchar(200)) = $(Slozka)
    -> FeatureWriter_2 [Sorted]
Note: "@SubstringRegularExpression(@Value(Cesta k Seznamu),^(.*[\\\/]),0,0,0,caseSensitive=TRUE)\Report.xlsx"
FeatureWriter_2
    DATASET = @Value(A)\@Value(B)\Report.xlsx
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = Yes
    XLSXW_FIELD_NAMES_FORMATTING = Yes
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TRUNCATE_TABLE = Yes
    XLSXW_WRITER_MODE = Insert

FME custom transformer FileDeleter
Delete specified file - not using Python, but rather the FeatureWriter - Copy File approach to remove the file. 
Image by OpenClipart-Vectors from Pixabay

Parameters:
- FileToDelete =   # File to delete (full path including filename)

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    SUMMARY -> Output (output)
Output (output)

FME custom transformer FeatureHolderExt
FeatureHolder Extended.
All input features cause hold but only those on the 'keep' port are passed to the output. Those on 'discard' are not passed through.
FeatureHolder Extended.
All input features cause hold but only those on the 'keep' port are passed to the output. Those on 'discard' are not passed through.

Keep (input)
    -> FeatureHolder
Discard (input)
    -> AttributeCreator
AttributeCreator
    ATTR_TABLE = SET_TO markForDiscard = t
    -> FeatureHolder
FeatureHolder
    -> isKept
isKept: Tester
    BOOL_OP = OR
    TEST_CLAUSE = TEST markForDiscard ATTRIBUTE_IS_MISSING ""
    TEST_MODE = Automatic
    PASSED -> AttributeRemover
AttributeRemover
    REMOVE_ATTRS = markForDiscard
    -> Kept (output)
Kept (output)

FME custom transformer EquipmentID_checker

Parameters:
- EQUIPMENTID = @Value(EquipmentID)   # EquipmentID
- ROWID = @Value(RowID)   # RowID

Input (input)
    -> AttributeSplitter
AttributeSplitter
    ATTR_NAME = EquipmentID
    DELIMITER = ~
    DROP_EMPTY_PARTS = No
    LIST_NAME = EquipmentID_list
    TRIM_OPTION = Both
    -> ListExploder
ListExploder
    ATTR_ACCUM_MODE = Merge List Attributes
    ATTR_CONFLICT_RES = Use List Attribute Values
    INDEX_ATTR = _element_index
    LIST_ATTR = EquipmentID_list{}
    ELEMENTS -> AttributeCreator_2
AttributeCreator_2
    ATTR_TABLE = SET_TO Lenght_EquipmentID (varchar(200)) = @StringLength(@Value(EquipmentID_list))
    -> Sorter
Sorter
    SORT_PARM = RowID NUMERIC ASCENDING Lenght_EquipmentID NUMERIC DESCENDING
    SORTED -> DuplicateFilter
DuplicateFilter
    INPUT_ORDERED_CHOICE = Yes
    KEYATTR = RowID
    UNIQUE -> Tester
Tester
    BOOL_OP = OR
    TEST_CLAUSE = TEST @Value(Lenght_EquipmentID) <= 30
    TEST_MODE = TEST
    PASSED -> Delka_ok (output)
    FAILED -> Delka_err (output)
Delka_ok (output)
Delka_err (output)
