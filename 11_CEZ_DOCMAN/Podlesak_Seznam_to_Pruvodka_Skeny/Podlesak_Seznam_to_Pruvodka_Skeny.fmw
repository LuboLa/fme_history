FME workspace Podlesak_Seznam_to_Pruvodka_Skeny.fmw

Parameters:
- API_PARAM_P_T = https://restapidv2.cezdata.corp/esb/ecm/document/v1/get-property-values/   # Produkce/Test
- Pevna_cesta = \\dfs03.cezdata.corp\CEZ\DKE\9050060_ŘTKE\TPKE\RIZEK\SKEN\   # Produkční,\\dfs03.cezdata.corp\CEZ\DKE\9050060_ŘTKE\TPKE\RIZEK\SKEN\ Produkce/Test
- KPJM = kucharovmar   # Zadajte KPJM
- Slozka = ETU\OB_00_ETU_Skenované dokumenty   # Slozka se souborem
- FME_JOB_ID = 1   # FME Flow Job ID

Note: Uprava att Stavba_H
Stavba_H: AttributeValueMapper
    DEFAULT_VALUE = CHYBA
    DIRECTION = Forward (Source To Destination)
    LUT = PPC,PPCEPC,PPCEPC,PPCEPC,ELE,ELE,NZELE6,ELE,EPR,EPR,ETU,ETU,ETU2,ETU,EGT,EGT,TTR-EKO,TTR
    SRC = Stavba_H
    VAL_ATTR = Stavba_H
    -> OJ_FME
OJ_FME: AttributeValueMapper
    DEFAULT_VALUE = CHYBA
    DIRECTION = Forward (Source To Destination)
    LUT = EDE,Nezadáno,EGT,Energotrans,EHO,Nezadáno,ELE,Elektrárna Ledvice,EME,Nezadáno,EPC,Nezadáno,PPCEPC,Elektrárna PPC Počerady,EPO,Nezadáno,EPR,Elektrárna Prunéřov,TTR,Teplárna Trmice,ETU,Elektrárna Tušimice
    SRC = Stavba_H
    VAL_ATTR = OJ_FME
    -> Nazev_typu_dokumentace_FME
Note: Chyby, které se odchytávají: / - Maker/CompanyIssuing není v čísleníku DM / - SO není v čísleníku DM / - PS není v čísleníku DM / - Dokument je vícekrát v Seznamu / - Řádek nemá vyplněn všechny atributy (kromě KKS) / - Seznam obsahuje soubory, které nejsou v zájmové složce / - V zájmové složce jsou soubory neobsažené v Seznamu
Nazev_typu_dokumentace_FME: AttributeValueMapper
    DEFAULT_VALUE = CHYBA
    DIRECTION = Forward (Source To Destination)
    LUT = TD,04 - Technická dokumentace (TD),PTD,05 - Průvodní technická dokumentace (PTD),DSP,06 - Dokumentace skutečného stavu (As Built),PD,03 - Projektová dokumentace (PD),OST,02 - Dokumenty managementu - Ostatní
    SRC = Kod dokumentace_H
    VAL_ATTR = Nazev_typu_dokumentace_FME
    -> TestFilter
TestFilter
    DEFAULT_VALUE = Některý atribut je prázdný
    PASSED_TEST_GROUP_OUTPUT = FIRST
    TEST_LIST:
      "BOOL_OP,AND,COMPOSITE_TEST,""""""1 AND 2 AND 3 AND 4 AND 5 AND 6 AND 7 AND 8 AND 9 AND 10 AND 11 AND 12 AND 13"""""",TEST_CLAUSE,TEST OB_H ATTRIBUTE_HAS_A_VALUE ""
      TEST SO_H ATTRIBUTE_HAS_A_VALUE ""
      TEST PS_H ATTRIBUTE_HAS_A_VALUE ""
      TEST DPS_H ATTRIBUTE_HAS_A_VALUE ""
      TEST Výrobní blok_H ATTRIBUTE_HAS_A_VALUE ""
      TEST Popis svazku s dokumentaci_H ATTRIBUTE_HAS_A_VALUE ""
      TEST Evidencni cislo svazku_H ATTRIBUTE_HAS_A_VALUE ""
      TEST Stavba_H ATTRIBUTE_HAS_A_VALUE ""
      TEST Datum kompletace dokumentace_H ATTRIBUTE_HAS_A_VALUE ""
      TEST Pocet listu_H ATTRIBUTE_HAS_A_VALUE ""
      TEST Zhotovitel (zkratka)_H ATTRIBUTE_HAS_A_VALUE ""
      TEST Kod dokumentace_H ATTRIBUTE_HAS_A_VALUE ""
      TEST Kod souboru dokumentu_H ATTRIBUTE_HAS_A_VALUE """,Všechny atributy jsou vyplněné
    Všechny atributy jsou vyplněné -> AttributeCreator
    Některý atribut je prázdný -> AttributeKeeper
Junction_9
    -> FeatureMerger_6 [REQUESTOR]
    -> FeatureMerger_3 [REQUESTOR]
Note: \Fáze 06 - Realizace\TC 02 - Snížení emisí NOx\06 - Dokumentace skutečného stavu (As Built)\ / \Fáze 06 - Realizace\TC 03 - snížení koncentrace Hg ve spalinách\06 - Dokumentace skutečného stavu (As Built)\
Note: Chyby na číselník vyřazuji v následujícím kroku z chybového Excelu
FeatureMerger_3
    ATTR_ACCUM_MODE = Merge Supplier
    ATTR_CONFLICT_RES = Use Requestor
    IGNORE_NULLS = No
    JOIN_KEYS = @Value(fme_feature_type) @Value(Evidencni cislo svazku_H) AUTO
    MERGE_TYPE = Attributes Only
    PROCESS_DUPS = NO
    REJECT_NULL_MISSING_KEYS = No
    SUPPLIERS_FIRST = No
    MERGED -> FeatureMerger_4 [REQUESTOR]
Note: UnmergedRequestor - Svazek neni v Registru svazků
FeatureMerger_6
    ATTR_ACCUM_MODE = Merge Supplier
    ATTR_CONFLICT_RES = Use Requestor
    IGNORE_NULLS = No
    JOIN_KEYS = @Value(fme_feature_type) @Value(Evidencni cislo svazku_H) AUTO
    MERGE_TYPE = Attributes Only
    PROCESS_DUPS = NO
    REJECT_NULL_MISSING_KEYS = No
    SUPPLIERS_FIRST = No
    MERGED -> FeatureMerger [REQUESTOR]

Bookmark: Číselník Docman - RestAPI
Creator_3
    GEOMTYPE = Geometry Object
    NUM = 1
    CREATED -> HTTPCaller
HTTPCaller
    ADDITIONAL_URL_PARAMETERS = DomainName;%
    AUTH_METHOD = Basic
    AUTH_PASSWORD =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
    AUTH_USERNAME = qpfmeserver
    CONNECTION_TIMEOUT_LENGTH = 60
    CUSTOM_HEADERS = messageId;$(FME_JOB_ID) timestamp;@DateTimeNow() sourceSystem;FME Server
    ERROR_ATTR = _error
    FOLLOW_REDIRECTS = FOLLOW_WITH_GET
    HTTP_METHOD = GET
    MAX_HTTP_VERSION = HTTP_1_1
    MAX_TRANSFERS_IN_PROGRESS = 10
    MINIMUM_ENCRYPTION_LEVEL = OS_DEFAULT
    MULTIPART_RESPONSE_HEADER_LIST_ATTR = _multipart_headers
    REDIRECT_AUTH = ORIGINAL_DOMAIN_ONLY
    RESPONSE_TYPE = Attribute
    SPLIT_MULTIPART_DOWNLOADS = YES
    TARGET_ATTR = _response_body
    TARGET_ATTR_ENCODING = fme-system
    TARGET_URL = $(API_PARAM_P_T)
    TRANSFER_TIMEOUT_LENGTH = 90
    USE_COOKIES = No
    VERIFY_SSL_CERTIFICATES = No
    -> AttributeCreator_4
AttributeCreator_4
    ATTR_TABLE = SET_TO _response_body = {"features":@Value(_response_body)}
    -> JSONFragmenter_2
JSONFragmenter_2
    EXPLODE_FORMAT = JSON
    EXTRACT_ATTR = Yes
    JSON_ATTR = _response_body
    JSON_QUERY = json["features"][*]
    READ_FROM_FILE = NO
    RECURSIVE = Yes
    REJECT_EMPTY_LISTS = YES
    FRAGMENTS -> AttributeExposer_2
AttributeExposer_2
    ATTR_LIST = value,domainName,description
    -> AttributeKeeper_7
AttributeKeeper_7
    CREATE_BULK_MODE_FEATURES = NO
    KEEP_ATTRS = description,domainName,value
    -> TestFilter_3
TestFilter_3
    DEFAULT_VALUE = <UNFILTERED>
    PASSED_TEST_GROUP_OUTPUT = FIRST
    TEST_LIST = "BOOL_OP,OR,COMPOSITE_TEST,""""""1"""""",TEST_CLAUSE,TEST @Value(domainName) = CompanyIssuing",CompanyIssuing,"BOOL_OP,OR,COMPOSITE_TEST,""""""1"""""",TEST_CLAUSE,TEST @Value(domainName) = DocumentSubType",DocumentSubType,"BOOL_OP,OR,COMPOSITE_TEST,""""""1"""""",TEST_CLAUSE,TEST @Value(domainName) = DocumentType",DocumentType,"BOOL_OP,OR,COMPOSITE_TEST,""""""1"""""",TEST_CLAUSE,TEST @Value(domainName) = SegmentationaccordingtoCSNEN6135A1",SegmentationaccordingtoCSNEN6135A1,"BOOL_OP,OR,COMPOSITE_TEST,""""""1"""""",TEST_CLAUSE,TEST @Value(domainName) = SegmentationaccordingtoCSNEN6135A3",SegmentationaccordingtoCSNEN6135A3,"BOOL_OP,OR,COMPOSITE_TEST,""""""1"""""",TEST_CLAUSE,TEST @Value(domainName) = PS",PS,"BOOL_OP,OR,COMPOSITE_TEST,""""""1"""""",TEST_CLAUSE,TEST @Value(domainName) = SO",SO,"BOOL_OP,OR,COMPOSITE_TEST,""""""1"""""",TEST_CLAUSE,TEST @Value(domainName) = DPS",DPS
    CompanyIssuing -> Test_ciselniku_Company_Issuing [SUPPLIER]
    DocumentSubType -> Test_ciselniku_Doc_SubType [SUPPLIER]
    DocumentType -> Test_ciselniku_Doc_Type [SUPPLIER]
    SegmentationaccordingtoCSNEN6135A1 -> Test_ciselniku_DCC_A1 [SUPPLIER]
    SegmentationaccordingtoCSNEN6135A3 -> Test_ciselniku_DCC_A2A3_2 [SUPPLIER]
    PS -> Test_ciselniku_PS_DPS [SUPPLIER]
SQLCreator
    DATASET = vypskp_PSK_READ
    EXPOSED_ATTRIBUTE_LIST = SO,Docman_code
    FORMAT = ORACLE_NONSPATIAL
    ORACLE_NONSPATIAL_CREATE_FEATURE_TABLES_FROM_DATA = Yes
    ORACLE_NONSPATIAL_NAMED_CONNECTION = vypskp_PSK_READ
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    OUTPUT_FEATURES_DISPLAY = Data Features
    SQL_STATEMENT:
      SELECT
          "A1"."CODE"   "SO",
          "A1"."DOCMAN_CODE"   "Docman_code"
      FROM
          "PSK_RP"."CV_SO" "A1"
    RESULT -> DuplicateFilter_4
DuplicateFilter_4
    INPUT_ORDERED_CHOICE = No
    KEYATTR = Docman_code SO
    UNIQUE -> Test_ciselniku_SO [SUPPLIER]

Bookmark: Načtení Seznamu ze zadané složky
Creator_2
    GEOMTYPE = Geometry Object
    NUM = 1
    CREATED -> AttributeManager_14
AttributeManager_14
    ATTR_TABLE:
      SET_TO Pevna_cesta (varchar(200)) = $(Pevna_cesta)
      SET_TO Slozka (varchar(200)) = $(Slozka)
    -> FeatureReader_4 [INITIATOR]
Note: Vylistuje soubor "TTR-EKO_TC02_seznam_AsB.xls" v kombinaci pevně dané cesty a uživatelsky dodaném názvu složky
FeatureReader_4
    ATTRIBUTES = PATH,"path_unix,path_windows,path_rootname,path_filename,path_extension,path_directory_unix,path_directory_windows,path_type,fme_geometry{0}"
    ATTR_ACCUM_MODE = Merge Initiator and Result
    ATTR_CONFLICT_RES = Use Result
    ATTR_IGNORE_NULLS = No
    COMBINE_GEOM = Use Result
    DATASET = @Value(Pevna_cesta)\@Value(Slozka)
    FORMAT = PATH
    OUTPUT_FEATURES_DISPLAY = Data Features
    PATH_HIDDEN_FILES = EXCLUDE
    PATH_NO_EMPTY_PROPERTIES = YES
    PATH_OFFSET_DATETIME = yes
    PATH_RECURSE_DIRECTORIES = NO
    PATH_RETRIEVE_FILE_PROPERTIES = NO
    PATH_TYPE = FILE
    PATH_USE_NON_STRING_ATTR = yes
    PATH -> TestFilter_4
TestFilter_4
    DEFAULT_VALUE = <UNFILTERED>
    PASSED_TEST_GROUP_OUTPUT = FIRST
    TEST_LIST = "BOOL_OP,OR,COMPOSITE_TEST,""""""1"""""",TEST_CLAUSE,CASE_SENSITIVE_TEST @Value(path_filename) CONTAINS_REGEX (^Report)|(^transmittal_sheet)",Report/transmital_sheet - smazat,"BOOL_OP,OR,COMPOSITE_TEST,""""""1"""""",TEST_CLAUSE,CASE_INSENSITIVE_TEST @Value(path_filename) CONTAINS_REGEX sken",Sken - zpracovat
    Report/transmital_sheet - smazat -> FileDeleter
    Sken - zpracovat -> FeatureHolderExt [Keep]
FileDeleter
    FileToDelete = @Value(path_windows)
    -> FeatureHolderExt [Discard]
FeatureHolderExt
    Kept -> AttributeManager_8
Note: Přejmenuje a posílá dál název a cestu k Seznamu
AttributeManager_8
    ATTR_TABLE:
      RENAME_SET_VALUE path_windows > Cesta k Seznamu
      RENAME_SET_VALUE path_directory_windows > Cesta ke slozce Seznamu
      RENAME_SET_VALUE path_rootname > Název Seznamu bez prip
      RENAME_SET_VALUE path_filename > Název Seznamu
      REMOVE path_unix
      REMOVE path_extension
      REMOVE path_directory_unix
      REMOVE path_type
      REMOVE fme_geometry{0}
      REMOVE fme_geometry{}
      REMOVE _creation_instance
    -> FeatureReader_5 [INITIATOR]
    -> Junction_3
    -> Junction_4

Bookmark: Příprava na kontrolu, zda jsou soubory opravdu ve složce dle Průvodky
Junction_4
    -> Sampler_2
    -> FeatureMerger_7 [SUPPLIER]
Sampler_2
    RATE = 1
    SAMPLE_MODE = No
    SAMPLE_TYPE_LONG = First N Features
    SAMPLED -> FeatureReader_7 [INITIATOR]
FeatureReader_7
    ATTRIBUTES = PATH,"path_unix,path_windows,path_rootname,path_filename,path_extension,path_directory_unix,path_directory_windows,path_type,fme_geometry{0}"
    ATTR_ACCUM_MODE = Merge Initiator and Result
    ATTR_CONFLICT_RES = Use Result
    ATTR_IGNORE_NULLS = No
    COMBINE_GEOM = Use Result
    DATASET = @Value(Pevna_cesta)\@Value(Slozka)
    FORMAT = PATH
    OUTPUT_FEATURES_DISPLAY = Data Features
    PATH_GLOB_PATTERN = *.pdf
    PATH_HIDDEN_FILES = EXCLUDE
    PATH_NO_EMPTY_PROPERTIES = YES
    PATH_OFFSET_DATETIME = yes
    PATH_RECURSE_DIRECTORIES = YES
    PATH_RETRIEVE_FILE_PROPERTIES = NO
    PATH_TYPE = FILE
    PATH_USE_NON_STRING_ATTR = yes
    PATH -> FeatureMerger_7 [REQUESTOR]
Note: Odeberu Seznamy, ze kterých se načítaji data
FeatureMerger_7
    ATTR_ACCUM_MODE = Merge Supplier
    ATTR_CONFLICT_RES = Use Requestor
    IGNORE_NULLS = No
    JOIN_KEYS = @Value(path_filename) @Value(Název Seznamu) AUTO
    MERGE_TYPE = Attributes Only
    PROCESS_DUPS = NO
    REJECT_NULL_MISSING_KEYS = No
    SUPPLIERS_FIRST = No
    UNMERGED_REQUESTOR -> AttributeKeeper_3
AttributeKeeper_3
    CREATE_BULK_MODE_FEATURES = NO
    KEEP_ATTRS = path_filename,path_windows
    -> FeatureMerger [SUPPLIER]

Bookmark: Načtení dat z hlavičkového listu _H (Header)
Note: Načte data hlavičkového listu z excelu
FeatureReader_5
    ATTR_ACCUM_MODE = Merge Initiator and Result
    ATTR_CONFLICT_RES = Use Result
    ATTR_IGNORE_NULLS = No
    COMBINE_GEOM = Use Result
    DATASET = @Value(Cesta k Seznamu)
    FEATURETYPES = Registr svazků  Seznam svazku
    FORMAT = XLSXR
    INTERACT = NONE
    OUTPUT_FEATURES_DISPLAY = Data Features
    XLSXR_ALLOW_DOLLAR_SIGNS = YES
    XLSXR_APPLY_FILTERS = No
    XLSXR_CASE_SENSITIVE_FEATURE_TYPES = YES
    XLSXR_CREATE_FEATURE_TABLES_FROM_DATA = Yes
    XLSXR_EXCEL_COL_NAMES = YES
    XLSXR_EXPAND_MERGED_CELLS = Yes
    XLSXR_FORCE_DATETIME = NO
    XLSXR_QUERY_FEATURE_TYPES_FOR_MERGE_FILTERS = Yes
    XLSXR_READ_BLANK_AS = Missing
    XLSXR_READ_FORM_CONTROLS = NONE
    XLSXR_READ_RASTER_MODE = None
    XLSXR_REPLACE_ONLY_NEWLINES_CARRIAGE_RETURNS = YES
    XLSXR_SCAN_MAX_FEATURES = 1000
    XLSXR_SCHEMA_HANDLING_REVISION = 2
    XLSXR_SKIP_EMPTY_ROWS = YES
    XLSXR_STRIP_SHEETNAME_SPACES = YES
    XLSXR_TRIM_ATTR_NAME_WHITESPACE = Yes
    XLSXR_USE_CUSTOM_SCHEMA = NO
    XLSXR_XLSXR_EXPOSE_FORMAT_ATTRS = xlsx_row_id,number(11,0)
    <OTHER> -> AttributeExposer_3
AttributeExposer_3
    ATTR_LIST = A,B,C,D,E,F,G,H,I,J,K,L,M,fme_feature_type,xlsx_row_id
    -> TestFilter_2
Note: Ořiznutí popisu dat
TestFilter_2
    DEFAULT_VALUE = <UNFILTERED>
    PASSED_TEST_GROUP_OUTPUT = FIRST
    TEST_LIST = "BOOL_OP,OR,COMPOSITE_TEST,""""""1"""""",TEST_CLAUSE,TEST @Value(xlsx_row_id) >= 3",@Value(xlsx_row_id) >= 3
    @Value(xlsx_row_id) >= 3 -> ABC_na_nazvy_v_Seznamu_2
Note: Přejmenování atributů
ABC_na_nazvy_v_Seznamu_2: AttributeRenamer
    ATTR_TABLE:
      RENAME_SET_DEFAULT A > OB_H
      RENAME_SET_DEFAULT B > SO_H
      RENAME_SET_DEFAULT C > PS_H
      RENAME_SET_DEFAULT D > DPS_H
      RENAME_SET_DEFAULT E > Výrobní blok_H
      RENAME_SET_DEFAULT F > Popis svazku s dokumentaci_H
      RENAME_SET_DEFAULT G > Evidencni cislo svazku_H
      RENAME_SET_DEFAULT H > Stavba_H
      RENAME_SET_DEFAULT I > Datum kompletace dokumentace_H
      RENAME_SET_DEFAULT J > Pocet listu_H
      RENAME_SET_DEFAULT K > Zhotovitel (zkratka)_H
      RENAME_SET_DEFAULT L > Kod dokumentace_H
      RENAME_SET_DEFAULT M > Kod souboru dokumentu_H
      RENAME_SET_DEFAULT xlsx_row_id > Cislo radku_H
    MISSING_INPUT_ATTRS = REMOVE
    -> Odstrani_tab_2

Bookmark: Předúprava atributů - odstranení nev. znaků
Odstrani_tab_2: StringReplacer
    CASE = NO
    FIND_TEXT = "\n"
    NO_MATCH = _FME_NO_OP_
    REGEXP = NO
    SRC_ATTRS = Cislo radku_H,Datum kompletace dokumentace_H,DPS_H,Evidencni cislo svazku_H,Kod dokumentace_H,Kod souboru dokumentu_H,OB_H,Pocet listu_H,Popis svazku s dokumentaci_H,PS_H,SO_H,Stavba_H,Výrobní blok_H,Zhotovitel (zkratka)_H
    -> Odstrani_enter_2
Odstrani_enter_2: StringReplacer
    CASE = NO
    FIND_TEXT = "    "
    NO_MATCH = _FME_NO_OP_
    REGEXP = NO
    SRC_ATTRS = Cislo radku_H,Datum kompletace dokumentace_H,DPS_H,Evidencni cislo svazku_H,Kod dokumentace_H,Kod souboru dokumentu_H,OB_H,Pocet listu_H,Popis svazku s dokumentaci_H,PS_H,SO_H,Stavba_H,Výrobní blok_H,Zhotovitel (zkratka)_H
    -> AttributeTrimmer_2
AttributeTrimmer_2
    SRC_ATTRS = "Cislo radku_H","Datum kompletace dokumentace_H",DPS_H,"Evidencni cislo svazku_H","Kod dokumentace_H","Kod souboru dokumentu_H",OB_H,"Pocet listu_H","Popis svazku s dokumentaci_H",PS_H,SO_H,Stavba_H,"Výrobní blok_H","Zhotovitel (zkratka)_H"
    TRIM_TO_NONE = Yes
    TRIM_TYPE = Both
    -> Stavba_H

Bookmark: Kontrola hlavičky na číselník
AttributeCreator
    ATTR_TABLE = SET_TO Hodnoty v ciselniku = 0
    -> Test_ciselniku_Company_Issuing [REQUESTOR]
Test_ciselniku_Company_Issuing: FeatureMerger
    ATTR_ACCUM_MODE = Merge Supplier
    ATTR_CONFLICT_RES = Use Requestor
    IGNORE_NULLS = No
    JOIN_KEYS = @Value(Zhotovitel (zkratka)_H) @Value(value) AUTO
    MERGE_TYPE = Attributes Only
    PROCESS_DUPS = NO
    REJECT_NULL_MISSING_KEYS = No
    SUPPLIERS_FIRST = No
    MERGED -> AttributeManager_6
    UNMERGED_REQUESTOR -> Test_ciselniku_PS_DPS [REQUESTOR]
    UNMERGED_REQUESTOR -> Popis_chyby_duplicitni_cesta_2
AttributeManager_6
    ATTR_TABLE:
      SET_TO Hodnoty v ciselniku = @Evaluate(@Value(Hodnoty v ciselniku)+1)
      REMOVE value
      REMOVE domainName
      REMOVE description
    -> Test_ciselniku_PS_DPS [REQUESTOR]
Test_ciselniku_PS_DPS: FeatureMerger
    ATTR_ACCUM_MODE = Merge Supplier
    ATTR_CONFLICT_RES = Use Requestor
    IGNORE_NULLS = No
    JOIN_KEYS = @Value(PS_H) @Value(value) AUTO
    MERGE_TYPE = Attributes Only
    PROCESS_DUPS = NO
    REJECT_NULL_MISSING_KEYS = No
    SUPPLIERS_FIRST = No
    MERGED -> AttributeManager
    UNMERGED_REQUESTOR -> Test_ciselniku_SO [REQUESTOR]
    UNMERGED_REQUESTOR -> Popis_chyby_duplicitni_cesta_3
AttributeManager
    ATTR_TABLE:
      SET_TO Hodnoty v ciselniku = @Evaluate(@Value(Hodnoty v ciselniku)+1)
      REMOVE value
      REMOVE domainName
      REMOVE description
    -> Test_ciselniku_SO [REQUESTOR]
Note: Zaškrtnuto Duplicitní Suppliers, ikdyž duplicitní nejsou, jinak nefunguje, nevím
Test_ciselniku_SO: FeatureMerger
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(SO_H) @Value(SO) AUTO @Value(Stavba_H) @Value(Docman_code) AUTO
    MERGE_TYPE = Attributes Only
    PROCESS_DUPS = YES
    REJECT_NULL_MISSING_KEYS = No
    SUPPLIERS_FIRST = No
    MERGED -> AttributeManager_3
    UNMERGED_REQUESTOR -> Tester_3
    UNMERGED_REQUESTOR -> Popis_chyby_duplicitni_cesta_4
AttributeManager_3
    ATTR_TABLE:
      SET_TO Hodnoty v ciselniku = @Evaluate(@Value(Hodnoty v ciselniku)+1)
      REMOVE SO
      REMOVE Docman_code
    -> Tester_3
Note: Value = 3, až bude fungovat propisování číselníku
Tester_3
    BOOL_OP = OR
    TEST_CLAUSE = TEST @Value(Hodnoty v ciselniku) = 3
    TEST_MODE = TEST
    PASSED -> FeatureMerger_6 [SUPPLIER]
    FAILED -> FeatureMerger_3 [SUPPLIER]
Popis_chyby_duplicitni_cesta_4: AttributeCreator
    ATTR_TABLE:
      SET_TO Atribut (buffer) = SO
      SET_TO Hodnota atributu (varchar(200)) = @Value(SO_H)
      SET_TO Popis chyby (buffer) = SO není v číselníku
    -> Junction
Popis_chyby_duplicitni_cesta_3: AttributeCreator
    ATTR_TABLE:
      SET_TO Atribut (buffer) = PS
      SET_TO Hodnota atributu (varchar(200)) = @Value(PS_H)
      SET_TO Popis chyby (buffer) = PS (DPS) není v číselníku
    -> Junction
Popis_chyby_duplicitni_cesta_2: AttributeCreator
    ATTR_TABLE:
      SET_TO Atribut (buffer) = Zhotovitel
      SET_TO Hodnota atributu (varchar(200)) = @Value(Zhotovitel (zkratka)_H)
      SET_TO Popis chyby (buffer) = Zhotovitel není v číselníku
    -> Junction
Note: Sorter : Input
Junction
    -> AttributeKeeper

Bookmark: Načtení dat z datových listů _D(Data)
Junction_3
    -> FeatureReader_6 [INITIATOR]
Note: Načte data z jednotlivých listů
FeatureReader_6
    ATTR_ACCUM_MODE = Merge Initiator and Result
    ATTR_CONFLICT_RES = Use Result
    ATTR_IGNORE_NULLS = No
    COMBINE_GEOM = Use Result
    DATASET = @Value(Cesta k Seznamu)
    FORMAT = XLSXR
    INTERACT = NONE
    OUTPUT_FEATURES_DISPLAY = Data Features
    XLSXR_ALLOW_DOLLAR_SIGNS = YES
    XLSXR_APPLY_FILTERS = No
    XLSXR_CASE_SENSITIVE_FEATURE_TYPES = YES
    XLSXR_CONFIGURATION_DATASET = U:\CEZ\DKE\9050060_ŘTKE\TPKE\RIZEK\JMA\TTR\TTR-EKO_TC02_seznam_AsB.xls
    XLSXR_CREATE_FEATURE_TABLES_FROM_DATA = Yes
    XLSXR_EXCEL_COL_NAMES = YES
    XLSXR_EXPAND_MERGED_CELLS = No
    XLSXR_FORCE_DATETIME = NO
    XLSXR_QUERY_FEATURE_TYPES_FOR_MERGE_FILTERS = Yes
    XLSXR_READ_BLANK_AS = Missing
    XLSXR_READ_FORM_CONTROLS = NONE
    XLSXR_READ_RASTER_MODE = None
    XLSXR_REPLACE_ONLY_NEWLINES_CARRIAGE_RETURNS = YES
    XLSXR_SCAN_MAX_FEATURES = 1000
    XLSXR_SCHEMA_HANDLING_REVISION = 2
    XLSXR_SKIP_EMPTY_ROWS = YES
    XLSXR_STRIP_SHEETNAME_SPACES = YES
    XLSXR_TABLELIST = List1
    XLSXR_TRIM_ATTR_NAME_WHITESPACE = Yes
    XLSXR_USE_CUSTOM_SCHEMA = YES
    XLSXR_XLSXR_EXPOSE_FORMAT_ATTRS = xlsx_row_id,number(11,0)
    <OTHER> -> AttributeExposer_5
AttributeExposer_5
    ATTR_LIST = "Oblast tisku pro analogový seznam dokumentů","Oblast tisku pro analogový seznam dokumentů00","Oblast tisku pro analogový seznam dokumentů01","Oblast tisku pro analogový seznam dokumentů02","Oblast tisku pro analogový seznam dokumentů03","Oblast tisku pro analogový seznam dokumentů04","Oblast tisku pro analogový seznam dokumentů05","Oblast tisku pro analogový seznam dokumentů06",TISK,TISK00,TISK01,"Informace o uložení","Printed Range for Analog Documents List","Printed Range for Analog Documents List00","Printed Range for Analog Documents List01","Printed Range for Analog Documents List02","Printed Range for Analog Documents List03","Printed Range for Analog Documents List04","Printed Range for Analog Documents List06",PRINT,PRINT00,PRINT01,"Storage Information",xlsx_row_id,fme_feature_type,"Ostatní informace00","Ostatní informace01"
    -> Tester_5
Note: Neprojde List1, Registr svazků a Vzor KE
Tester_5
    BOOL_OP = OR
    TEST_CLAUSE:
      TEST @Value(fme_feature_type) = Registr svazků
      TEST @Value(fme_feature_type) = Seznam svazku
      TEST @Value(fme_feature_type) = Seznam dokumentace VZOR
      TEST @Value(fme_feature_type) = List1
    TEST_MODE = TEST
    FAILED -> Row_ID_vetsirovno_11
Note: Filtruje hlavičku svazku
Row_ID_vetsirovno_11: Tester
    BOOL_OP = OR
    TEST_CLAUSE = TEST @Value(xlsx_row_id) >= 11
    TEST_MODE = TEST
    PASSED -> TestFilter_6
    FAILED -> TestFilter_5
Note: Domluva s Maruškou, vymazané Cesty el souboru jsou duplicitní
TestFilter_6
    DEFAULT_VALUE = <UNFILTERED>
    PASSED_TEST_GROUP_OUTPUT = FIRST
    TEST_LIST:
      "BOOL_OP,AND,COMPOSITE_TEST,""""""1 AND 2 AND 3"""""",TEST_CLAUSE,TEST Oblast tisku pro analogový seznam dokumentů ATTRIBUTE_HAS_A_VALUE ""
      TEST Informace o uložení ATTRIBUTE_HAS_A_VALUE ""
      TEST Printed Range for Analog Documents List NOT_ATTRIBUTE_HAS_A_VALUE """,CZ,"BOOL_OP,AND,COMPOSITE_TEST,""""""1 AND 2 AND 3"""""",TEST_CLAUSE,TEST Printed Range for Analog Documents List ATTRIBUTE_HAS_A_VALUE ""
      TEST Storage Information ATTRIBUTE_HAS_A_VALUE ""
      TEST Oblast tisku pro analogový seznam dokumentů NOT_ATTRIBUTE_HAS_A_VALUE """,EN
    CZ -> AttributeManager_9
    EN -> AttributeManager_10
Note: Přejmenování a sjednocení atributů
AttributeManager_9
    ATTR_TABLE:
      RENAME_SET_VALUE Oblast tisku pro analogový seznam dokumentů > Poradove cislo_D
      RENAME_SET_VALUE Oblast tisku pro analogový seznam dokumentů00 > KKS_D
      RENAME_SET_VALUE Oblast tisku pro analogový seznam dokumentů01 > Název a typ zarizeni, systemu, celku_D
      RENAME_SET_VALUE Oblast tisku pro analogový seznam dokumentů02 > Popis dokumentu_D
      RENAME_SET_VALUE Oblast tisku pro analogový seznam dokumentů03 > Archivni cislo_D
      RENAME_SET_VALUE Oblast tisku pro analogový seznam dokumentů04 > Revize dokumentu_D
      RENAME_SET_VALUE Oblast tisku pro analogový seznam dokumentů05 > Výrobce_D
      RENAME_SET_VALUE Oblast tisku pro analogový seznam dokumentů06 > Pocet listu_D
      RENAME_SET_VALUE Informace o uložení > Cesta elektronickeho souboru_D
      RENAME_SET_VALUE TISK > DCCA1_D
      RENAME_SET_VALUE TISK00 > DCCA2_D
      RENAME_SET_VALUE TISK01 > DCCA3_D
      RENAME_SET_VALUE xlsx_row_id > Cislo radku_D
      REMOVE Printed Range for Analog Documents List
      REMOVE Printed Range for Analog Documents List00
      REMOVE Printed Range for Analog Documents List01
      REMOVE Printed Range for Analog Documents List02
      REMOVE Printed Range for Analog Documents List03
      REMOVE Printed Range for Analog Documents List04
      REMOVE Printed Range for Analog Documents List06
      REMOVE Storage Information
      REMOVE PRINT
      REMOVE PRINT00
      REMOVE PRINT01
      REMOVE Ostatní informace00
      REMOVE Ostatní informace01
    -> FeatureJoiner_2 [LEFT]
Note: Přejmenování a sjednocení atributů (EN -> CZ)
AttributeManager_10
    ATTR_TABLE:
      RENAME_SET_VALUE Printed Range for Analog Documents List > Poradove cislo_D
      RENAME_SET_VALUE Printed Range for Analog Documents List00 > KKS_D
      RENAME_SET_VALUE Printed Range for Analog Documents List01 > Název a typ zarizeni, systemu, celku_D
      RENAME_SET_VALUE Printed Range for Analog Documents List02 > Popis dokumentu_D
      RENAME_SET_VALUE Printed Range for Analog Documents List03 > Archivni cislo_D
      RENAME_SET_VALUE Printed Range for Analog Documents List04 > Revize dokumentu_D
      RENAME_SET_VALUE Printed Range for Analog Documents List06 > Pocet listu_D
      RENAME_SET_VALUE Storage Information > Cesta elektronickeho souboru_D
      RENAME_SET_VALUE PRINT > DCCA1_D
      RENAME_SET_VALUE PRINT00 > DCCA2_D
      RENAME_SET_VALUE PRINT01 > DCCA3_D
      RENAME_SET_VALUE xlsx_row_id > Cislo radku_D
      REMOVE Ostatní informace00
      REMOVE Oblast tisku pro analogový seznam dokumentů
      REMOVE Oblast tisku pro analogový seznam dokumentů00
      REMOVE Oblast tisku pro analogový seznam dokumentů01
      REMOVE Oblast tisku pro analogový seznam dokumentů02
      REMOVE Oblast tisku pro analogový seznam dokumentů03
      REMOVE Oblast tisku pro analogový seznam dokumentů04
      REMOVE Oblast tisku pro analogový seznam dokumentů06
      REMOVE Informace o uložení
      REMOVE TISK
      REMOVE TISK00
      REMOVE TISK01
      REMOVE Ostatní informace01
    USER_EXPOSED_ATTRIBUTES = Oblast tisku pro analogový seznam dokumentů05,Printed Range for Analog Documents List05
    -> FeatureJoiner_2 [LEFT]
Note: Získání Typo a Podtypu dokumentu z datového listu
TestFilter_5
    DEFAULT_VALUE = Nezájem
    PASSED_TEST_GROUP_OUTPUT = FIRST
    TEST_LIST = "BOOL_OP,OR,COMPOSITE_TEST,""""""1"""""",TEST_CLAUSE,TEST @Value(xlsx_row_id) = 3",Typ dokumentace,"BOOL_OP,OR,COMPOSITE_TEST,""""""1"""""",TEST_CLAUSE,TEST @Value(xlsx_row_id) = 4",Podtyp dokumentace
    Typ dokumentace -> AttributeManager_15
    Podtyp dokumentace -> AttributeManager_16
AttributeManager_15
    ATTR_TABLE:
      RENAME_SET_VALUE Ostatní informace00 > Typ dokumentu_D
      RENAME_SET_VALUE Ostatní informace01 > Slozka_lvl4 = FME_CONDITIONAL:DEFAULT_VALUE'FME_NULL_VALUE'BOOL_OP;AND;COMPOSITE_TEST;1 AND 2;TEST Slozka_lvl4 ATTRIBUTE_HAS_A_VALUE _FME_BLANK_STRING_;CASE_INSENSITIVE_TEST @Value(Slozka_lvl4) NOT_CONTAINS Poznámka'\@Value(Slozka_lvl4)'FME_NUM_CONDITIONS2___
      REMOVE Oblast tisku pro analogový seznam dokumentů
      REMOVE Oblast tisku pro analogový seznam dokumentů00
      REMOVE Oblast tisku pro analogový seznam dokumentů01
      REMOVE Oblast tisku pro analogový seznam dokumentů02
      REMOVE Oblast tisku pro analogový seznam dokumentů03
      REMOVE Oblast tisku pro analogový seznam dokumentů04
      REMOVE Oblast tisku pro analogový seznam dokumentů06
      REMOVE Informace o uložení
      REMOVE TISK
      REMOVE TISK00
      REMOVE TISK01
      REMOVE Printed Range for Analog Documents List
      REMOVE Printed Range for Analog Documents List00
      REMOVE Printed Range for Analog Documents List01
      REMOVE Printed Range for Analog Documents List02
      REMOVE Printed Range for Analog Documents List03
      REMOVE Printed Range for Analog Documents List04
      REMOVE Printed Range for Analog Documents List06
      REMOVE Storage Information
      REMOVE PRINT
      REMOVE PRINT00
      REMOVE PRINT01
      REMOVE xlsx_row_id
      REMOVE Pevna_cesta
      REMOVE Slozka
      REMOVE Cesta k Seznamu
      REMOVE Cesta ke slozce Seznamu
      REMOVE Název Seznamu bez prip
    -> FeatureJoiner [LEFT]
AttributeManager_16
    ATTR_TABLE:
      RENAME_SET_VALUE Ostatní informace00 > Podtyp dokumentu_D
      RENAME_SET_VALUE Ostatní informace01 > Slozka_lvl5 = FME_CONDITIONAL:DEFAULT_VALUE'FME_NULL_VALUE'BOOL_OP;OR;COMPOSITE_TEST;1;TEST Slozka_lvl5 ATTRIBUTE_HAS_A_VALUE _FME_BLANK_STRING_'\@Value(Slozka_lvl5)'FME_NUM_CONDITIONS2___
      REMOVE Oblast tisku pro analogový seznam dokumentů
      REMOVE Oblast tisku pro analogový seznam dokumentů00
      REMOVE Oblast tisku pro analogový seznam dokumentů01
      REMOVE Oblast tisku pro analogový seznam dokumentů02
      REMOVE Oblast tisku pro analogový seznam dokumentů03
      REMOVE Oblast tisku pro analogový seznam dokumentů04
      REMOVE Oblast tisku pro analogový seznam dokumentů06
      REMOVE Informace o uložení
      REMOVE TISK
      REMOVE TISK00
      REMOVE TISK01
      REMOVE Printed Range for Analog Documents List
      REMOVE Printed Range for Analog Documents List00
      REMOVE Printed Range for Analog Documents List01
      REMOVE Printed Range for Analog Documents List02
      REMOVE Printed Range for Analog Documents List03
      REMOVE Printed Range for Analog Documents List04
      REMOVE Printed Range for Analog Documents List06
      REMOVE Storage Information
      REMOVE PRINT
      REMOVE PRINT00
      REMOVE PRINT01
      REMOVE xlsx_row_id
      REMOVE Pevna_cesta
      REMOVE Slozka
      REMOVE Cesta k Seznamu
      REMOVE Cesta ke slozce Seznamu
      REMOVE Název Seznamu bez prip
    -> FeatureJoiner [RIGHT]
FeatureJoiner
    ATTR_CONFLICT_RES = Prefer Left
    GEOMETRY_HANDLING = Prefer Left
    JOIN_KEYS = fme_feature_type fme_feature_type AUTO Název Seznamu Název Seznamu AUTO
    JOIN_MODE = Full
    JOINED -> FeatureJoiner_2 [RIGHT]
FeatureJoiner_2
    ATTR_CONFLICT_RES = Prefer Left
    GEOMETRY_HANDLING = Prefer Left
    JOIN_KEYS = Název Seznamu Název Seznamu AUTO fme_feature_type fme_feature_type AUTO
    JOIN_MODE = Inner
    JOINED -> Nahrada_carky_za_tildu

Bookmark: Dodatečná úprava KKS (EquipmentID)
Nahrada_carky_za_tildu: StringReplacer
    CASE = NO
    FIND_TEXT = ,
    NO_MATCH = _FME_NO_OP_
    REGEXP = NO
    REPLACE_TEXT = ~
    SRC_ATTRS = KKS_D
    -> Nahrada_mezery_za_nic
Nahrada_mezery_za_nic: StringReplacer
    CASE = NO
    FIND_TEXT = " "
    NO_MATCH = _FME_NO_OP_
    REGEXP = NO
    SRC_ATTRS = KKS_D
    -> Nahrada_podtrzitka_za_nic
Nahrada_podtrzitka_za_nic: StringReplacer
    CASE = NO
    FIND_TEXT = _
    NO_MATCH = _FME_NO_OP_
    REGEXP = NO
    SRC_ATTRS = KKS_D
    -> NullAttributeMapper

Bookmark: Kontrola vyplnění povinných dat
NullAttributeMapper
    ATTRCHOICE = Selected Attributes
    ATTRLIST = Archivni cislo_D Cesta elektronickeho souboru_D Cislo radku_D DCCA1_D DCCA2_D DCCA3_D KKS_D Název a typ zarizeni, systemu, celku_D Pocet listu_D Podtyp dokumentu_D Poradove cislo_D Revize dokumentu_D Typ dokumentu_D Popis dokumentu_D
    NULL_TREATMENT = Null
    SOURCE_ATTR_VAL = "Missing (Selected Attributes Only)"
    -> AttributeValidator
AttributeValidator
    TABLE = Archivni cislo_D,Cesta elektronickeho souboru_D,DCCA1_D,DCCA2_D,DCCA3_D,Název a typ zarizeni, systemu, celku_D,Pocet listu_D,Podtyp dokumentu_D,Revize dokumentu_D,Typ dokumentu_D,Popis dokumentu_D;ATTRIBUTE_HAS_A_VALUE;<Unused>
    PASSED -> DuplicateFilter
    FAILED -> ListExploder
Note: ListExploder / An attribute may fail multiple tests / Split the list to create one record per test message
ListExploder
    ATTR_ACCUM_MODE = Merge List Attributes
    ATTR_CONFLICT_RES = Use List Attribute Values
    INDEX_ATTR = _element_index
    LIST_ATTR = _fme_validation_message_list{}
    ELEMENTS -> AttributeExploder
Note: AttributeExploder / Create a set of name/value pairs : for each test
AttributeExploder
    ATTR_NAME_LABEL = _attr_name
    ATTR_VALUE_LABEL = _attr_value
    EXPLODING_TYPE = Features
    KEEP_ATTRIBUTES = Yes
    KEEP_GEOMETRY = No
    -> StringSearcher
Note: StringSearcher / Find name/value pairs that have an error message
StringSearcher
    CASE = no
    MATCHED_RESULT_ATTR = _first_match
    REGEXP = '@Value(_attr_name)'
    STRING_TO_SEARCH = @Value(_fme_validation_message_list)
    MATCHED -> TestFilter_7
TestFilter_7
    DEFAULT_VALUE = <UNFILTERED>
    PASSED_TEST_GROUP_OUTPUT = FIRST
    TEST_LIST = "BOOL_OP,OR,COMPOSITE_TEST,""""""1"""""",TEST_CLAUSE,CASE_INSENSITIVE_TEST @Value(_fme_validation_message_list) CONTAINS Has a value",Has a Value
    Has a Value -> Popis_chyby_vyplneni_atributu
Note: Chyba = odstranění feature
Popis_chyby_vyplneni_atributu: AttributeCreator
    ATTR_TABLE:
      SET_TO Atribut = @Value(_attr_name)
      SET_TO Hodnota atributu = NULL
      SET_TO Popis chyby = Hodnota chybí
      SET_TO Cesta elektronickeho souboru = @Value(Pevna_cesta)\@Value(Slozka)\@Value(Cesta elektronickeho souboru_D)
      SET_TO Sheet_name = Chyby v Seznamu dokumentace
    -> AttributeKeeper

Bookmark: Kontrola na duplicitní záznamy souborů v Seznamu
Note: Duplicitní soubory 2x načtené - chyba
DuplicateFilter
    INPUT_ORDERED_CHOICE = No
    KEYATTR = Cesta elektronickeho souboru_D
    UNIQUE -> FeatureMerger_5 [REQUESTOR]
    UNIQUE -> Test_ciselniku_DCC_A2A3_2 [REQUESTOR]
    DUPLICATE -> FeatureMerger_5 [SUPPLIER]
FeatureMerger_5
    ATTR_ACCUM_MODE = Merge Supplier
    ATTR_CONFLICT_RES = Use Requestor
    IGNORE_NULLS = No
    JOIN_KEYS = @Value(Cesta elektronickeho souboru_D) @Value(Cesta elektronickeho souboru_D) AUTO
    MERGE_TYPE = Attributes Only
    PROCESS_DUPS = NO
    REJECT_NULL_MISSING_KEYS = No
    SUPPLIERS_FIRST = No
    MERGED -> Popis_chyby_duplicitni_cesta
    USED_SUPPLIER -> Popis_chyby_duplicitni_cesta
Popis_chyby_duplicitni_cesta: AttributeCreator
    ATTR_TABLE:
      SET_TO Atribut (buffer) = Cesta elektronickeho souboru
      SET_TO Hodnota atributu (varchar(200)) = @Value(Cesta elektronickeho souboru_D)
      SET_TO Popis chyby (buffer) = Duplicitní "Cesta elektronického souboru". Dokument načten vícekrát
    -> Junction_12
Note: Sorter : Input
Note: Chyby
Junction_12
    -> AttributeKeeper

Bookmark: New Bookmark
Test_ciselniku_DCC_A2A3_2: FeatureMerger
    ATTR_ACCUM_MODE = Merge Supplier
    ATTR_CONFLICT_RES = Use Requestor
    IGNORE_NULLS = No
    JOIN_KEYS = @Value(DCCA2_D)@Value(DCCA3_D) @Value(value) AUTO
    MERGE_TYPE = Attributes Only
    PROCESS_DUPS = NO
    REJECT_NULL_MISSING_KEYS = Yes
    SUPPLIERS_FIRST = No
    MERGED -> Test_ciselniku_DCC_A1 [REQUESTOR]
    UNMERGED_REQUESTOR -> Popis_chyby_DCC_A2A3
    UNMERGED_REQUESTOR -> Test_ciselniku_DCC_A1 [REQUESTOR]
    <REJECTED> -> Popis_chyby_DCC_A2A3
    <REJECTED> -> Test_ciselniku_DCC_A1 [REQUESTOR]
Popis_chyby_DCC_A2A3: AttributeCreator
    ATTR_TABLE:
      SET_TO Atribut = DCC A2A3
      SET_TO Hodnota atributu = @Value(DCCA2_D)@Value(DCCA3_D)
      SET_TO Popis chyby = Není v číselníku
    -> DuplicateFilter_5

Bookmark: New Bookmark
Test_ciselniku_DCC_A1: FeatureMerger
    ATTR_ACCUM_MODE = Merge Supplier
    ATTR_CONFLICT_RES = Use Requestor
    IGNORE_NULLS = No
    JOIN_KEYS = @Value(DCCA1_D) @Value(value) AUTO
    MERGE_TYPE = Attributes Only
    PROCESS_DUPS = NO
    REJECT_NULL_MISSING_KEYS = Yes
    SUPPLIERS_FIRST = No
    MERGED -> Test_ciselniku_Doc_Type [REQUESTOR]
    UNMERGED_REQUESTOR -> Popis_chyby_DCC_A1_2
    UNMERGED_REQUESTOR -> Test_ciselniku_Doc_Type [REQUESTOR]
    <REJECTED> -> Popis_chyby_DCC_A1_2
    <REJECTED> -> Test_ciselniku_Doc_Type [REQUESTOR]
Popis_chyby_DCC_A1_2: AttributeCreator
    ATTR_TABLE:
      SET_TO Atribut = DCC A1
      SET_TO Hodnota atributu = @Value(DCCA1_D)
      SET_TO Popis chyby = Není v číselníku
    -> DuplicateFilter_5

Bookmark: New Bookmark
Test_ciselniku_Doc_Type: FeatureMerger
    ATTR_ACCUM_MODE = Merge Supplier
    ATTR_CONFLICT_RES = Use Requestor
    IGNORE_NULLS = No
    JOIN_KEYS = @Value(Typ dokumentu_D) @Value(value) AUTO
    MERGE_TYPE = Attributes Only
    PROCESS_DUPS = NO
    REJECT_NULL_MISSING_KEYS = Yes
    SUPPLIERS_FIRST = No
    MERGED -> Test_ciselniku_Doc_SubType [REQUESTOR]
    UNMERGED_REQUESTOR -> Popis_chyby_Typ_dokumentu_2
    UNMERGED_REQUESTOR -> Test_ciselniku_Doc_SubType [REQUESTOR]
    <REJECTED> -> Popis_chyby_Typ_dokumentu_2
    <REJECTED> -> Test_ciselniku_Doc_SubType [REQUESTOR]
Popis_chyby_Typ_dokumentu_2: AttributeCreator
    ATTR_TABLE:
      SET_TO Atribut = Typ dokumentu
      SET_TO Hodnota atributu = @Value(Typ dokumentu_D)
      SET_TO Popis chyby = Není v číselníku
    -> DuplicateFilter_5

Bookmark: New Bookmark
Test_ciselniku_Doc_SubType: FeatureMerger
    ATTR_ACCUM_MODE = Merge Supplier
    ATTR_CONFLICT_RES = Use Requestor
    IGNORE_NULLS = No
    JOIN_KEYS = @Value(Podtyp dokumentu_D) @Value(value) AUTO
    MERGE_TYPE = Attributes Only
    PROCESS_DUPS = NO
    REJECT_NULL_MISSING_KEYS = No
    SUPPLIERS_FIRST = No
    MERGED -> Junction_7
    UNMERGED_REQUESTOR -> Popis_chyby_SubType_2
    UNMERGED_REQUESTOR -> Junction_7
    <REJECTED> -> Popis_chyby_SubType_2
    <REJECTED> -> Junction_7
Popis_chyby_SubType_2: AttributeCreator
    ATTR_TABLE:
      SET_TO Atribut = Podtyp dokumentu
      SET_TO Hodnota atributu = @Value(Podtyp dokumentu_D)
      SET_TO Popis chyby = Hodnota neni v číselníku
    -> DuplicateFilter_5

Bookmark: Kontrola dle číselníků nebo pravidel
Junction_7
    -> AttributeRemover
AttributeRemover
    REMOVE_ATTRS = description,domainName,value
    -> FeatureMerger_9 [REQUESTOR]
DuplicateFilter_5
    INPUT_ORDERED_CHOICE = No
    KEYATTR = Cislo radku_D
    UNIQUE -> FeatureMerger_9 [SUPPLIER]
    UNIQUE -> Junction_10
    DUPLICATE -> Junction_10
Note: Odebere chybové záznamy
FeatureMerger_9
    ATTR_ACCUM_MODE = Merge Supplier
    ATTR_CONFLICT_RES = Use Requestor
    IGNORE_NULLS = No
    JOIN_KEYS = @Value(Cislo radku_D) @Value(Cislo radku_D) AUTO
    MERGE_TYPE = Attributes Only
    PROCESS_DUPS = NO
    REJECT_NULL_MISSING_KEYS = No
    SUPPLIERS_FIRST = No
    UNMERGED_REQUESTOR -> Junction_2
Junction_10
    -> AttributeKeeper

Bookmark: Odstarnění duplicity z Cesty k seznamu vs Cesty elektronického souboru
Junction_2
    -> Sampler_3
    -> FeatureMerger_11 [REQUESTOR]
Sampler_3
    RATE = 1
    SAMPLE_MODE = No
    SAMPLE_TYPE_LONG = First N Features
    SAMPLED -> AttributeKeeper_2
AttributeKeeper_2
    CREATE_BULK_MODE_FEATURES = NO
    KEEP_ATTRS = Cesta ke slozce Seznamu,Cesta elektronickeho souboru_D
    -> AttributeSplitter_2
    -> AttributeSplitter
AttributeSplitter_2
    ATTR_NAME = Cesta ke slozce Seznamu
    DELIMITER = \
    DROP_EMPTY_PARTS = Yes
    LIST_NAME = _list
    TRIM_OPTION = Both
    -> ListExploder_2
ListExploder_2
    ATTR_ACCUM_MODE = Merge List Attributes
    ATTR_CONFLICT_RES = Use List Attribute Values
    INDEX_ATTR = _element_index
    LIST_ATTR = _list{}
    ELEMENTS -> FeatureMerger_10 [REQUESTOR]
AttributeSplitter
    ATTR_NAME = Cesta elektronickeho souboru_D
    DELIMITER = \
    DROP_EMPTY_PARTS = Yes
    LIST_NAME = _list
    TRIM_OPTION = Both
    -> ListExploder_3
ListExploder_3
    ATTR_ACCUM_MODE = Merge List Attributes
    ATTR_CONFLICT_RES = Use List Attribute Values
    INDEX_ATTR = _element_index
    LIST_ATTR = _list{}
    ELEMENTS -> FeatureMerger_10 [SUPPLIER]
FeatureMerger_10
    ATTR_ACCUM_MODE = Merge Supplier
    ATTR_CONFLICT_RES = Use Requestor
    IGNORE_NULLS = No
    JOIN_KEYS = @Value(Cesta elektronickeho souboru_D) @Value(Cesta elektronickeho souboru_D) AUTO @Value(_list) @Value(_list) AUTO
    MERGE_TYPE = Attributes Only
    PROCESS_DUPS = NO
    REJECT_NULL_MISSING_KEYS = No
    SUPPLIERS_FIRST = No
    MERGED -> Sorter_3
Sorter_3
    SORT_PARM = _element_index NATURAL ASCENDING
    SORTED -> Aggregator
Aggregator
    ACCUM_ATTRS_NAME = Merge Incoming Attributes
    AGGREGATE_TYPE = Homogeneous Collection (If Possible)
    CONCAT_ATTRS = _list
    MODE = Geometry - Assemble One Level
    SEP = \
    AGGREGATE -> StringReplacer
StringReplacer
    CASE = NO
    FIND_TEXT = @Value(_list)\
    NO_MATCH = _FME_NO_OP_
    REGEXP = NO
    SRC_ATTRS = Cesta ke slozce Seznamu
    -> AttributeManager_4
AttributeManager_4
    ATTR_TABLE:
      REMOVE Cesta elektronickeho souboru_D (varchar(200))
      RENAME_SET_VALUE Cesta ke slozce Seznamu > Cesta k OB_FME (buffer)
      RENAME_SET_VALUE _list > Duplicitni cast cesty_FME (varchar(200))
      REMOVE _element_index (uint32)
    -> FeatureMerger_11 [SUPPLIER]
Note: Celej tenhle nesmysl slouží jen k tomu, aby se správně vytvořilo cesta k souboru. Seznam neleží na stejné úrovni jako OBXX, ale Cesta elektronického souboru začíná OBXX\...
FeatureMerger_11
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Cesta_elektronickeho_souboru_D
Cesta_elektronickeho_souboru_D: StringReplacer
    CASE = NO
    FIND_TEXT = @Value(Duplicitni cast cesty_FME)\
    NO_MATCH = _FME_NO_OP_
    REGEXP = NO
    SRC_ATTRS = Cesta elektronickeho souboru_D
    -> Junction_9

Bookmark: Kontrola souborů Seznam vs soubory ve složce
FeatureMerger
    ATTR_ACCUM_MODE = Merge Supplier
    ATTR_CONFLICT_RES = Use Requestor
    IGNORE_NULLS = No
    JOIN_KEYS = @LowerCase(@Value(Cesta k OB_FME)@Value(Duplicitni cast cesty_FME)\@Value(Cesta elektronickeho souboru_D)) @LowerCase(@Value(path_windows)) STRING
    MERGE_TYPE = Attributes Only
    PROCESS_DUPS = NO
    REJECT_NULL_MISSING_KEYS = No
    SUPPLIERS_FIRST = No
    MERGED -> AttributeManager_11
    UNMERGED_REQUESTOR -> AttributeCreator_3
    UNUSED_SUPPLIER -> FeatureMerger_4 [SUPPLIER]
AttributeCreator_3
    ATTR_TABLE:
      SET_TO Název listu (varchar(200)) = @Value(Evidencni cislo svazku_H)
      SET_TO Atribut (buffer) = Cesta elektronickeho souboru
      SET_TO Hodnota atributu (buffer) = -
      SET_TO Cesta elektronickeho souboru (varchar(200)) = @Value(Cesta elektronickeho souboru_D)
      SET_TO Filename (varchar(200)) = @SubstringRegularExpression(@Value(Cesta elektronickeho souboru_D),(?:[^\\/](?!(\\|/)))+$,0,0,0,caseSensitive=TRUE)
    -> Junction_8
FeatureMerger_4
    ATTR_ACCUM_MODE = Merge Supplier
    ATTR_CONFLICT_RES = Use Requestor
    IGNORE_NULLS = No
    JOIN_KEYS = @Value(Cesta k OB_FME)@Value(Duplicitni cast cesty_FME)\@Value(Cesta elektronickeho souboru_D) @Value(path_windows) AUTO
    MERGE_TYPE = Attributes Only
    PROCESS_DUPS = NO
    REJECT_NULL_MISSING_KEYS = No
    SUPPLIERS_FIRST = No
    UNUSED_SUPPLIER -> AttributeCreator_5
    <REJECTED> -> AttributeCreator_5
Note: Vypnutá větev, pozor
AttributeCreator_5 [off]
    ATTR_TABLE:
      SET_TO Název listu (buffer) = NA
      SET_TO Atribut (buffer) = NA
      SET_TO Hodnota atributu (buffer) = NA
      SET_TO Cesta elektronickeho souboru (buffer) = NA
      SET_TO Filename (buffer) = @Value(path_filename)
    -> Junction_8
Note: Chyba
Junction_8
    -> AttributeKeeper

Bookmark: Mapování atributů
Note: Typ dokumentu se svazku R4 / Podtyp dokumentu ze svazku R4 / Zhotovitel ze Seznamu svazku K
AttributeManager_11
    ATTR_TABLE:
      SET_TO AuthorDM = $(KPJM)
      SET_TO Code = @Value(Stavba_H)
      SET_TO CompanyIssuing = @Value(Zhotovitel (zkratka)_H)
      SET_TO Date = @DateTimeFormat(@DateTimeNow(),%Y-%m-%d)
      SET_TO DocumentDescription = @Value(Popis dokumentu_D)
      SET_TO DocumentState = 20
      SET_TO DocumentSubject = @Value(Název a typ zarizeni, systemu, celku_D)
      SET_TO DocumentSubType = @Value(Podtyp dokumentu_D)
      SET_TO DocumentTitle = @Value(Popis dokumentu_D) / @Value(Název a typ zarizeni, systemu, celku_D) // @Value(Archivni cislo_D)
      SET_TO DocumentType = @Value(Typ dokumentu_D)
      SET_TO DPS = @Value(DPS_H)
      SET_TO EquipmentID = @Value(KKS_D)
      SET_TO Id
      SET_TO ImportedDocument = true
      SET_TO Location = @Value(Stavba_H)
      SET_TO Maker = @Value(Výrobce_D)
      SET_TO OriginalDocumentVersionSeriesId
      SET_TO PackNumber = @Value(Kod dokumentace_H)/@Value(Kod souboru dokumentu_H)/@Value(Evidencni cislo svazku_H)
      SET_TO Phase
      SET_TO ProjectId = @Value(Stavba_H)
      SET_TO PS = @Value(PS_H)
      SET_TO Revision = @Value(Revize dokumentu_D)
      SET_TO SegmentationaccordingtoCSNEN6135A1 = @Value(DCCA1_D)
      SET_TO SegmentationaccordingtoCSNEN6135A3 = @Value(DCCA2_D)@Value(DCCA3_D)
      SET_TO Sheet = @Value(Pocet listu_D)
      SET_TO SO = @Value(SO_H)
      SET_TO SupplierArchivalNo = @Value(Archivni cislo_D)
      SET_TO TradePackage = SKEN
      SET_TO FileName = @Value(path_filename)
      SET_TO FileNetPath = @Value(OJ_FME)\Fáze 09 - Skenované dokumenty\SKEN - Skenované dokumenty\@Value(Nazev_typu_dokumentace_FME)@Value(Slozka_lvl4)@Value(Slozka_lvl5)\@Value(Evidencni cislo svazku_H)_@Value(Popis svazku s dokumentaci_H)
      SET_TO PathToFiles = @Value(Cesta elektronickeho souboru_D)
      REMOVE fme_feature_type
      REMOVE Cesta k Seznamu
      REMOVE Název Seznamu bez prip
      REMOVE Název Seznamu
    USER_EXPOSED_ATTRIBUTES = PathToFiles,Order,Oznaceni_PS_DPS,Doplnujici_nazev_predmetu_umisteni,Stav_dokumentu,Datum_vytvoreni,Typ_dokumentu_DMDI
    -> Counter

Bookmark: Multicontent
Counter
    CNT_ATTR = Count
    DOMAIN = counter
    SCOPE = Global
    START = 0
    -> AttributeKeeper_6
    -> FeatureMerger_8 [SUPPLIER]
AttributeKeeper_6
    CREATE_BULK_MODE_FEATURES = NO
    KEEP_ATTRS = SupplierArchivalNo,FileName,PathToFiles,FileNetPath,Count
    -> AttributeCreator_2
AttributeCreator_2
    ATTR_TABLE = SET_TO Extenze = @Substring(@Value(FileName),@add(@FindRegularExpression(@Value(FileName),(\.)(?!.*\.),0,0,0,caseSensitive=TRUE),1))
    -> AttributeValueMapper
AttributeValueMapper
    DEFAULT_VALUE = 5
    LUT = PDF,1,pdf,1,DOCX,2,docx,2,DOC,2,doc,2
    MAPPING_DIRECTION = FORWARD
    SRC = Extenze
    VAL_ATTR = Priorita extenze
    -> Sorter_2
Sorter_2
    SORT_PARM = Priorita extenze NUMERIC ASCENDING
    SORTED -> DuplicateFilter_2
DuplicateFilter_2
    INPUT_ORDERED_CHOICE = No
    KEYATTR = SupplierArchivalNo FileNetPath
    UNIQUE -> FeatureMerger_2 [REQUESTOR]
    DUPLICATE -> FeatureMerger_2 [SUPPLIER]
    DUPLICATE -> DuplicateFilter_3
FeatureMerger_2
    ATTR_ACCUM_MODE = Merge Supplier
    ATTR_CONFLICT_RES = Use Requestor
    IGNORE_NULLS = No
    JOIN_KEYS = @Value(SupplierArchivalNo) @Value(SupplierArchivalNo) AUTO @Value(FileNetPath) @Value(FileNetPath) AUTO
    LIST_ATTRS_TO_INCLUDE = FileName PathToFiles
    LIST_NAME = Multicontent
    MERGE_TYPE = Attributes Only
    PROCESS_DUPS = NO
    REJECT_NULL_MISSING_KEYS = No
    SUPPLIERS_FIRST = No
    MERGED -> ListConcatenator
    UNMERGED_REQUESTOR -> AttributeKeeper_8
ListConcatenator
    DROP_EMPTY_PARTS = Yes
    LIST_ATTR = Multicontent{}.FileName
    SEP = ~
    VAL_ATTR = FileName_Multi
    -> ListConcatenator_2
ListConcatenator_2
    DROP_EMPTY_PARTS = Yes
    LIST_ATTR = Multicontent{}.PathToFiles
    SEP = ~
    VAL_ATTR = PathToFiles_Multi
    -> AttributeManager_2
AttributeManager_2
    ATTR_TABLE:
      SET_TO FileName = @Value(FileName)~@Value(FileName_Multi)
      SET_TO PathToFiles = @Value(PathToFiles)~@Value(PathToFiles_Multi)
    USER_EXPOSED_ATTRIBUTES = FileNetPath,Filename_raw,Dup_FileNetPath,Dup_Filename_raw,path_directory_windows,Dup_path_directory_windows
    -> AttributeKeeper_8
AttributeKeeper_8
    CREATE_BULK_MODE_FEATURES = NO
    KEEP_ATTRS = FileName,PathToFiles,SupplierArchivalNo,Count
    -> FeatureMerger_8 [REQUESTOR]
FeatureMerger_8
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(Count) @Value(Count) AUTO
    MERGE_TYPE = Attributes Only
    PROCESS_DUPS = YES
    REJECT_NULL_MISSING_KEYS = No
    SUPPLIERS_FIRST = No
    MERGED -> StringReplacer_2
DuplicateFilter_3
    INPUT_ORDERED_CHOICE = No
    KEYATTR = SupplierArchivalNo FileNetPath

Bookmark: Zápis
StringReplacer_2
    CASE = NO
    FIND_TEXT = /
    NO_MATCH = _FME_NO_OP_
    REGEXP = NO
    REPLACE_TEXT = \
    SRC_ATTRS = FileNetPath,PathToFiles
    -> FeatureMerger_13 [REQUESTOR]
AttributeKeeper
    CREATE_BULK_MODE_FEATURES = NO
    KEEP_ATTRS = Atribut,fme_feature_type,Hodnota atributu,Název Seznamu,Popis chyby,Cislo radku_D
    -> Sorter
Sorter
    SORT_PARM = Název Seznamu NATURAL ASCENDING fme_feature_type NATURAL ASCENDING Cislo radku_D ALPHA ASCENDING Popis chyby NATURAL ASCENDING
    SORTED -> AttributeRenamer
AttributeRenamer
    ATTR_TABLE:
      RENAME_SET_DEFAULT fme_feature_type > Název listu
      RENAME_SET_DEFAULT Cislo radku_D > Cislo radku
    MISSING_INPUT_ATTRS = REMOVE
    -> StringReplacer_3
StringReplacer_3
    CASE = NO
    FIND_TEXT = _D$|_H$
    NO_MATCH = _FME_NO_OP_
    REGEXP = YES
    SRC_ATTRS = Atribut
    -> AttributeCreator_6
    -> FeatureMerger_13 [SUPPLIER]
AttributeCreator_6
    ATTR_TABLE:
      SET_TO Pevna_cesta (varchar(200)) = $(Pevna_cesta)
      SET_TO Slozka (varchar(200)) = $(Slozka)
    -> Report [Sorted]
Report: FeatureWriter
    DATASET = @Value(Pevna_cesta)\@Value(Slozka)\Report.xlsx
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = Yes
    XLSXW_FIELD_NAMES_FORMATTING = Yes
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TRUNCATE_TABLE = Yes
    XLSXW_WRITER_MODE = Insert
FeatureMerger_13
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = 1 1 AUTO
    MERGE_TYPE = Attributes Only
    PROCESS_DUPS = YES
    REJECT_NULL_MISSING_KEYS = No
    SUPPLIERS_FIRST = No
    UNMERGED_REQUESTOR -> AttributeCreator_7
AttributeCreator_7
    ATTR_TABLE:
      SET_TO Pevna_cesta (varchar(200)) = $(Pevna_cesta)
      SET_TO Slozka (varchar(200)) = $(Slozka)
    -> Transmital_sheet [Output]
Transmital_sheet: FeatureWriter
    CSV2_COORDINATE_SYSTEM_GRANULARITY = FEATURE_TYPE
    CSV2_DELIMITER = ;
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = @Value(Pevna_cesta)\@Value(Slozka)
    DATASET_ATTR = _dataset
    FEATURE_TYPE_LIST_ATTR = _feature_types
    FORMAT = CSV2
    TOTAL_FEATURES_WRITTEN_ATTR = _total_features_written

FME custom transformer FileDeleter
Delete specified file - not using Python, but rather the FeatureWriter - Copy File approach to remove the file. 
Image by OpenClipart-Vectors from Pixabay

Parameters:
- FileToDelete =   # File to delete (full path including filename)

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    SUMMARY -> Output (output)
Output (output)

FME custom transformer FeatureHolderExt
FeatureHolder Extended.
All input features cause hold but only those on the 'keep' port are passed to the output. Those on 'discard' are not passed through.
FeatureHolder Extended.
All input features cause hold but only those on the 'keep' port are passed to the output. Those on 'discard' are not passed through.

Keep (input)
    -> FeatureHolder
Discard (input)
    -> AttributeCreator
AttributeCreator
    ATTR_TABLE = SET_TO markForDiscard = t
    -> FeatureHolder
FeatureHolder
    -> isKept
isKept: Tester
    BOOL_OP = OR
    TEST_CLAUSE = TEST markForDiscard ATTRIBUTE_IS_MISSING ""
    TEST_MODE = Automatic
    PASSED -> AttributeRemover
AttributeRemover
    REMOVE_ATTRS = markForDiscard
    -> Kept (output)
Kept (output)
